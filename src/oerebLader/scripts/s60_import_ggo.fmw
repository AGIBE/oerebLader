FME workspace s60_import_ggo.fmw

Parameters:
- FGDB =   # File Geodatabase
- OUTPUT_RV_URL =   # Output-URL Rechtsvorschriften
- INPUT_RV_DIR =   # Input-Directory Rechtsvorschriften
- OUTPUT_RV_DIR =   # Output-Directory Rechtsvorschriften
- EXCEL_AMT =   # Source Microsoft Excel File AMT
- EXCEL_DARSTELLUNGSDIENST =   # Source Microsoft Excel File Darstellungsdienst
- LIEFEREINHEIT =   # Liefereinheit
- LEGEND_BASEURL =   # Base-URL Legende
- LEGEND_FULLURL =   # URL-Legendsymbol
- LOGFILE =   # Logfile
- WORK_CONNECTION =   # Connection to work
- GEODB_PG_DATABASE =   # Postgis Database
- GEODB_PG_USERNAME =   # Postgis Username
- GEODB_PG_PASSWORD =   # Postgis Password
- GEODB_PG_HOST =   # Postgis Host
- GEODB_PG_PORT =   # Postgis Port
- OEREB2_DATABASE =   # OEREB2 Database
- OEREB2_USERNAME =   # OEREB2 Username
- OEREB2_PASSWORD =   # OEREB2 Password
- OEREB2_CONNECTION =   # OEREB2 Conneciont
- OUTPUT_OBJBL_DIR =   # Outputdir Objektblätter
- OUTPUT_OBJBL_URL =   # Outputurl Objektblätter
- INPUT_OBJBL_DIR =   # Inputdir Objektblätter
- OEREB_PG_DATABASE =
- OEREB_PG_HOST =
- OEREB_PG_PASSWORD =
- OEREB_PG_PORT =
- OEREB_PG_USERNAME =
- RES_ID = 1   # Rechtsstatus
- STH_ID = 230   # Subthema ID
- DestDataset_FILECOPY = C:\Windows\Temp   # Destination File Copy Folder
- schema = regional_protected_geological_objects
- law_status = inForce
- topic = ch.BE.RegionalProtectedGeologicalObjects

Readers:
- GEODATABASE_FILE_1: GEODATABASE_FILE from $(FGDB) in EPSG:2056
- XLSXR_1: XLSXR from $(EXCEL_AMT)
- XLSXR_2: XLSXR from $(EXCEL_DARSTELLUNGSDIENST)

Writers:
- GEODATABASE_SDE_1: GEODATABASE_SDE in EPSG:2056
- POSTGIS_1: POSTGIS to $(GEODB_PG_DATABASE) in EPSG:2056
- GEODATABASE_SDE_2: GEODATABASE_SDE
- ORACLE_NONSPATIAL_1: ORACLE_NONSPATIAL to $(OEREB2_DATABASE)
- FILECOPY_1: FILECOPY to $(DestDataset_FILECOPY)
- POSTGRES_1: POSTGRES to $(OEREB_PG_DATABASE)
- POSTGRES_2: POSTGRES to $(OEREB_PG_DATABASE)
- POSTGRES_3: POSTGRES to $(OEREB_PG_DATABASE)
- POSTGRES_4: POSTGRES to $(OEREB_PG_DATABASE)
- POSTGIS_2: POSTGIS to $(OEREB_PG_DATABASE)
- POSTGRES_5: POSTGRES to $(OEREB_PG_DATABASE)
- POSTGRES_6: POSTGRES to $(OEREB_PG_DATABASE)
- POSTGRES_7: POSTGRES to $(OEREB_PG_DATABASE)
- POSTGRES_8: POSTGRES to $(OEREB_PG_DATABASE)

Note: GGO_GGO
GGO_GGOP (reader GEODATABASE_FILE_1)
    attributes: OBJECTID integer, GGO_NR smallint, GGO_ZUSNR smallint, GGO_NAME char(100), GGO_BED_D char(60), GGO_BED_F char(60), BESCHL_ART char(4), BESCHL_NR smallint, BESCHL_DAT date, E_KOORD double, N_KOORD double, GESTEIN char(80), PETRO_STRA char(80), HERKUNFT char(80), BEMERKUNG char(150), URL_BESCHL char(150), LAGE_GEN char(30), BED_WISS char(30), FLORA_SCH char(30), BEM_FL char(30), FINDLING char(4), URL_OBJBL char(150)
    -> PythonCaller
Note: Vorbereitung Kopie Dokumente
PythonCaller
    NEW_ATTRIBUTES = beschl_source_dataset beschl_dest_dataset objbl_source_dataset objbl_dest_dataset
    PYTHONSOURCE:
      # -*- coding: utf-8 -*-
      import fme
      import fmeobjects
      import os

      def FeatureProcessor(feature):
          beschl_doc = feature.getAttribute('URL_BESCHL')

          if not beschl_doc is None and beschl_doc != '':
              outputURL_beschl = FME_MacroValues['OUTPUT_RV_URL'] + beschl_doc

              inputFile_beschl = os.path.join(FME_MacroValues['INPUT_RV_DIR'], beschl_doc)
              inputFile_beschl = inputFile_beschl.replace('\\','/')

              outputDir_beschl = FME_MacroValues['OUTPUT_RV_DIR'].replace('\\','/')

              feature.setAttribute('URL_BESCHL', outputURL_beschl)
              feature.setAttribute('beschl_source_dataset', inputFile_beschl)
              feature.setAttribute('beschl_dest_dataset', outputDir_beschl)

          objbl_doc = feature.getAttribute('URL_OBJBL')

          if not objbl_doc is None and objbl_doc != '':
              outputURL_beschl = FME_MacroValues['OUTPUT_OBJBL_URL'] + objbl_doc

              inputFile_beschl = os.path.join(FME_MacroValues['INPUT_OBJBL_DIR'], objbl_doc)
              inputFile_beschl = inputFile_beschl.replace('\\','/')

              outputDir_beschl = FME_MacroValues['OUTPUT_OBJBL_DIR'].replace('\\','/')

              feature.setAttribute('URL_OBJBL', outputURL_beschl)
              feature.setAttribute('objbl_source_dataset', inputFile_beschl)
              feature.setAttribute('objbl_dest_dataset', outputDir_beschl)
    PYTHONSYMBOL = FeatureProcessor
    -> GEODB.GGO_GGOP (writer GEODATABASE_SDE_1)
    -> BulkAttributeRenamer
    -> Tester
    -> AttributeRemover_3
    -> Tester_2
Note: GEODB.GGO_GGOP
GEODB.GGO_GGOP (writer GEODATABASE_SDE_1)
    attributes: OBJECTID integer, GGO_NR smallint, GGO_ZUSNR smallint, GGO_NAME char(100), GGO_BED_D char(60), GGO_BED_F char(60), BESCHL_ART char(4), BESCHL_NR smallint, BESCHL_DAT date, E_KOORD double, N_KOORD double, GESTEIN char(80), PETRO_STRA char(80), HERKUNFT char(80), BEMERKUNG char(150), URL_BESCHL char(150), LAGE_GEN char(30), BED_WISS char(30), FLORA_SCH char(30), BEM_FL char(30), FINDLING char(4), URL_OBJBL char(150)
BulkAttributeRenamer
    ATTRCHOICE = All Attributes
    CASE_CHANGE_TYPE = lower
    MODE_CHOICE = RENAME
    PATTERN_ACTION_DISP = CASECHANGE
    -> ggo_ggop (writer POSTGIS_1)
Note: geodb.ggo_ggop
ggo_ggop (writer POSTGIS_1)
    attributes: objectid int4, ggo_nr int2, ggo_zusnr int2, ggo_name varchar(100), ggo_bed_d varchar(60), ggo_bed_f varchar(60), beschl_art varchar(4), beschl_nr int2, beschl_dat timestamp, e_koord float8, n_koord float8, gestein varchar(80), petro_stra varchar(80), herkunft varchar(80), bemerkung varchar(150), url_beschl varchar(150), lage_gen varchar(30), bed_wiss varchar(30), flora_sch varchar(30), bem_fl varchar(30), findling varchar(4), url_objbl varchar(150)
Tester_2
    BOOL_OP = AND
    TEST_CLAUSE:
      TEST URL_OBJBL NOT_ATTRIBUTE_VALUE_NULL ""
      TEST URL_OBJBL NOT_ATTRIBUTE_IS_EMPTY ""
      TEST URL_OBJBL NOT_ATTRIBUTE_IS_MISSING ""
    PASSED -> AttributeRemover_2
AttributeRemover_2
    REMOVE_ATTRS = FINDLING,GGO_ZUSNR,BESCHL_DAT,GESTEIN,OBJECTID,BED_WISS,GGO_NR,LAGE_GEN,BEMERKUNG,E_KOORD,beschl_dest_dataset,URL_OBJBL,GGO_BED_D,BESCHL_ART,BESCHL_NR,beschl_source_dataset,FLORA_SCH,HERKUNFT,BEM_FL,PETRO_STRA,N_KOORD,URL_BESCHL,GGO_NAME,GGO_BED_F
    -> Aggregator_2
Aggregator_2
    ACCUM_ATTRS_NAME = Drop Incoming Attributes
    AGGREGATE_TYPE = Homogeneous Collection (If Possible)
    GROUP_BY = objbl_source_dataset objbl_dest_dataset
    MODE = Geometry - Assemble One Level
    ORDERED = No
    SEP = ,
    AGGREGATE -> filecopy (writer FILECOPY_1)
Tester
    BOOL_OP = AND
    TEST_CLAUSE:
      TEST URL_BESCHL NOT_ATTRIBUTE_VALUE_NULL ""
      TEST URL_BESCHL NOT_ATTRIBUTE_IS_EMPTY ""
      TEST URL_BESCHL NOT_ATTRIBUTE_IS_MISSING ""
    PASSED -> AttributeRemover
AttributeRemover
    REMOVE_ATTRS = FINDLING,GGO_ZUSNR,BESCHL_DAT,GESTEIN,OBJECTID,BED_WISS,GGO_NR,LAGE_GEN,BEMERKUNG,E_KOORD,URL_OBJBL,GGO_BED_D,BESCHL_ART,BESCHL_NR,FLORA_SCH,objbl_source_dataset,HERKUNFT,objbl_dest_dataset,BEM_FL,PETRO_STRA,N_KOORD,URL_BESCHL,GGO_NAME,GGO_BED_F
    -> Aggregator
Aggregator
    ACCUM_ATTRS_NAME = Drop Incoming Attributes
    AGGREGATE_TYPE = Homogeneous Collection (If Possible)
    GROUP_BY = beschl_source_dataset beschl_dest_dataset
    MODE = Geometry - Assemble One Level
    ORDERED = No
    SEP = ,
    AGGREGATE -> filecopy (writer FILECOPY_1)
Note: RV_Copy
filecopy (writer FILECOPY_1)
    attributes: filecopy_source_dataset char(512), filecopy_dest_dataset char(512), filecopy_dest_filename char(128)
AttributeRemover_3
    REMOVE_ATTRS = N_KOORD,OBJECTID,GESTEIN,HERKUNFT,BEM_FL,Findling,GGO_BED_F,beschl_dest_dataset,FLORA_SCH,BED_WISS,beschl_source_dataset,PETRO_STRA,E_KOORD,OBJ_BLATT,GGO_BED_D,BEMERKUNG
    -> UUIDGenerator
Note: PUN_OID
UUIDGenerator
    UUID_ATTR = PUN_OID
    -> UUIDGenerator_2
Note: EIB_OID
UUIDGenerator_2
    UUID_ATTR = EIB_OID
    -> AttributeCreator
Note: Diverse Attribute
AttributeCreator
    ATTR_TABLE:
      SET_TO PUN_PUBLIZIERTAB = @Value(BESCHL_DAT)
      SET_TO EIB_AUSSAGE_DE = @Value(GGO_NAME) (GGO-Nr. @Value(GGO_NR))
      SET_TO EIB_AUSSAGE_FR = @Value(GGO_NAME) (No. OGP @Value(GGO_NR))
      SET_TO EIB_PUBLIZIERTAB = @Value(BESCHL_DAT)
      SET_TO EIB_LIEFEREINHEIT = $(LIEFEREINHEIT)
      SET_TO EIB_LEGENDESYMBOL_DE = $(LEGEND_FULLURL)
      SET_TO EIB_LEGENDESYMBOL_FR = $(LEGEND_FULLURL)
    -> FeatureMerger [REQUESTOR]
Note: AMT
AMT (reader XLSXR_1)
    attributes: AMT_OID char(20), AMT_NAME_DE char(73), AMT_NAME_FR char(73), AMT_AMTIMWEB_DE char(101), AMT_AMTIMWEB_FR char(102), AMT_LIEFEREINHEIT number(6,0), AMT_SPRACHE char(6)
    -> TestFilter
TestFilter
    DEFAULT_VALUE = <UNFILTERED>
    TEST_LIST = "BOOL_OP,OR,COMPOSITE_TEST,""""""<Unused>"""""",TEST_CLAUSE,TEST @Value(AMT_LIEFEREINHEIT) = $(LIEFEREINHEIT)",LIEFEREINHEIT
    LIEFEREINHEIT -> AttributeRenamer_5
    LIEFEREINHEIT -> AttributeKeeper_3
    LIEFEREINHEIT -> AMT (writer ORACLE_NONSPATIAL_1)
AttributeKeeper_3
    KEEP_ATTRS = AMT_LIEFEREINHEIT,AMT_OID
    -> FeatureMerger [SUPPLIER]
FeatureMerger
    ATTR_ACCUM_MODE = Merge Supplier
    ATTR_CONFLICT_RES = Use Requestor
    IGNORE_NULLS = No
    JOIN_KEYS = @Value(EIB_LIEFEREINHEIT) @Value(AMT_LIEFEREINHEIT) AUTO
    MERGE_TYPE = Attributes Only
    PROCESS_DUPS = NO
    REJECT_NULL_MISSING_KEYS = No
    SUPPLIERS_FIRST = No
    MERGED -> FeatureMerger_2 [REQUESTOR]
    UNMERGED_REQUESTOR -> Terminator
    UNUSED_SUPPLIER -> Terminator
    <REJECTED> -> Terminator
Terminator
    MESSAGE = Translation Terminated
AttributeRenamer_5
    ATTR_TABLE:
      RENAME_SET_DEFAULT AMT_OID > id
      RENAME_SET_DEFAULT AMT_AMTIMWEB_DE > office_at_web
      RENAME_SET_DEFAULT AMT_LIEFEREINHEIT > liefereinheit
    -> JSONTemplater [ROOT]
Note: Name-Attribut als JSON-String / aufbauen.
JSONTemplater
    RESULT_ATTRIBUTE = name
    ROOT_QUERY_EXPR:
      {
          "fr": fme:get-attribute("AMT_NAME_FR"),
          "de": fme:get-attribute("AMT_NAME_DE")
      }
    VISIBLE_QUERY_VALIDATE = Yes
    -> office (writer POSTGRES_1)
office (writer POSTGRES_1)
    attributes: id varchar(80),PrimaryKey, name json, office_at_web varchar(80), uid varchar(12), line1 varchar(80), line2 varchar(80), street varchar(80), number varchar(80), postal_code int4, city varchar(80), liefereinheit int4
Note: OEREB2.AMT
AMT (writer ORACLE_NONSPATIAL_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(6,0)
Note: DARSTELLUNGSDIENS
DARSTELLUNGSDIENST (reader XLSXR_2)
    attributes: DAR_OID char(15), DAR_VERWEISWMS_DE char(259), DAR_VERWEISWMS_FR char(259), DAR_LEGENDEIMWEB_DE char(11), DAR_LEGENDEIMWEB_FR char(11)
    -> AttributeCreator_2
Note: DAR_LIEFEREINHEIT
AttributeCreator_2
    ATTR_TABLE = SET_TO DAR_LIEFEREINHEIT = $(LIEFEREINHEIT)
    -> AttributeRemover_5
    -> StringConcatenator
AttributeRemover_5
    REMOVE_ATTRS = DAR_VERWEISWMS_DE,DAR_VERWEISWMS_FR,DAR_LEGENDEIMWEB_DE,DAR_LEGENDEIMWEB_FR
    -> FeatureMerger_2 [SUPPLIER]
FeatureMerger_2
    ATTR_ACCUM_MODE = Merge Supplier
    ATTR_CONFLICT_RES = Use Requestor
    IGNORE_NULLS = No
    JOIN_KEYS = @Value(EIB_LIEFEREINHEIT) @Value(DAR_LIEFEREINHEIT) AUTO
    MERGE_TYPE = Attributes Only
    PROCESS_DUPS = NO
    REJECT_NULL_MISSING_KEYS = No
    SUPPLIERS_FIRST = No
    MERGED -> PUNKT (writer GEODATABASE_SDE_2)
    MERGED -> Counter
    MERGED -> UUIDGenerator_3
    MERGED -> AttributeKeeper
    MERGED -> AttributeRenamer_4
    UNMERGED_REQUESTOR -> Terminator_2
    UNUSED_SUPPLIER -> Terminator_2
    <REJECTED> -> Terminator_2
AttributeRenamer_4
    ATTR_TABLE:
      RENAME_SET_DEFAULT PUN_OID > id
      RENAME_SET_DEFAULT PUN_PUBLIZIERTAB > published_from
      RENAME_SET_DEFAULT EIB_OID > public_law_restriction_id
      RENAME_SET_DEFAULT AMT_OID > office_id
    -> AttributeKeeper_2
AttributeKeeper_2
    KEEP_ATTRS = public_law_restriction_id,office_id,id,published_from
    -> AttributeCreator_10
AttributeCreator_10
    ATTR_TABLE = SET_TO schema = $(schema)
    -> geometry (writer POSTGIS_2)
geometry (writer POSTGIS_2)
    attributes: id varchar(80),PrimaryKey, law_status varchar(80), published_from date, geo_metadata varchar(80), public_law_restriction_id varchar(80), office_id varchar(80), liefereinheit int4
Note: OEREB2.PUNKT
PUNKT (writer GEODATABASE_SDE_2)
    attributes: OBJECTID integer, PUN_OID char(128), PUN_XTF_ID char(128), PUN_PUBLIZIERTAB date, PUN_METAGEO_DE char(1023), PUN_METAGEO_FR char(1023), PUN_LIEFEREINHEIT integer, EIB_OID char(128), AMT_OID char(128), RES_ID integer
Counter
    CNT_ATTR = EIB_SORT
    DOMAIN = counter
    SCOPE = Global
    START = 1
    -> EIGENTUMSBESCHRAENKUNG (writer ORACLE_NONSPATIAL_1)
    -> AttributeRenamer_11
    <REJECTED> -> Terminator_3
Terminator_3
    MESSAGE = Translation Terminated
Note: OEREB2.EIGENTUMSBESCHRAENKUNG
EIGENTUMSBESCHRAENKUNG (writer ORACLE_NONSPATIAL_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), STH_ID number(10,0), EIB_SORT number(10,0), EIB_LEGENDESYMBOL_DE nvarchar(1023), EIB_LEGENDESYMBOL_FR nvarchar(1023)
AttributeRenamer_11
    ATTR_TABLE:
      RENAME_SET_DEFAULT EIB_OID > plr_id
      RENAME_SET_DEFAULT EIB_PUBLIZIERTAB > published_from
      RENAME_SET_DEFAULT DAR_OID > view_service_id
      RENAME_SET_DEFAULT AMT_OID > office_id
      RENAME_SET_DEFAULT EIB_LEGENDESYMBOL_DE > symbol_url
    -> JSONTemplater_5 [ROOT]
Note: Information-Attribut als JSON-String / aufbauen.
JSONTemplater_5
    RESULT_ATTRIBUTE = information
    ROOT_QUERY_EXPR:
      {
          "fr": fme:get-attribute("EIB_AUSSAGE_FR"),
          "de": fme:get-attribute("EIB_AUSSAGE_DE")
      }
    VISIBLE_QUERY_VALIDATE = Yes
    -> AttributeKeeper_8
AttributeKeeper_8
    KEEP_ATTRS = information,published_from,symbol_url,plr_id,view_service_id,office_id
    -> AttributeCreator_16
Note: Aggregation in legend_entry / https://agimine.easyredmine.com/projects/einfuehrung-oereb-server/wiki/Aggregation
AttributeCreator_16
    ATTR_TABLE:
      SET_TO topic = $(topic)
      SET_TO liefereinheit = $(LIEFEREINHEIT)
      SET_TO sub_theme = FME_NULL_VALUE
      SET_TO schema = $(schema)
    -> Aggregator_10
public_law_restriction (writer POSTGRES_3)
    attributes: id varchar(80),PrimaryKey, information json, topic varchar(80), sub_theme json, other_theme varchar(80), type_code varchar(40), type_code_list varchar(80), law_status varchar(80), published_from date, view_service_id varchar(80), office_id varchar(80), liefereinheit int4
legend_entry (writer POSTGRES_4)
    attributes: id varchar(80),PrimaryKey, symbol varchar(80), symbol_url varchar(80), legend_text json, type_code varchar(40), type_code_list varchar(80), topic varchar(80), sub_theme json, other_theme varchar(80), view_service_id varchar(80), liefereinheit int4
Note: VOR_OID
UUIDGenerator_3
    UUID_ATTR = VOR_OID
    -> AttributeCreator_4
    -> UUIDGenerator_4
    -> AttributeRemover_6
Note: Diverse Attribute
AttributeCreator_4
    ATTR_TABLE:
      SET_TO VOR_TEXTIMWEB_DE = @Value(URL_BESCHL)
      SET_TO VOR_TEXTIMWEB_FR = @Value(URL_BESCHL)
      SET_TO VOR_OFFIZIELLENR = @Value(BESCHL_NR)
      SET_TO VOR_PUBLIZIERTAB = @Value(BESCHL_DAT)
      SET_TO VOA_ID = 1
    -> DateTimeConverter
Note: Datum vorbereiten für Verwendung in Titel
DateTimeConverter
    DATETIME_ATTR = BESCHL_DAT
    OUT_FORMAT = %d.%m.%Y
    REPAIR_INPUT = NO
    -> AttributeCreator_7
    <REJECTED> -> Terminator_4
Note: Titel
AttributeCreator_7
    ATTR_TABLE:
      SET_TO VOR_TITEL_DE = Schutzbeschluss @Value(BESCHL_ART) @Value(BESCHL_NR) vom @Value(BESCHL_DAT)
      SET_TO VOR_TITEL_FR = Décision de mise sous protection @Value(BESCHL_ART) @Value(BESCHL_NR) du @Value(BESCHL_DAT)
      SET_TO VOR_OFFIZIELLERTITEL_DE = Schutzbeschluss @Value(BESCHL_ART) @Value(BESCHL_NR) vom @Value(BESCHL_DAT)
      SET_TO VOR_OFFIZIELLERTITEL_FR = Décision de mise sous protection @Value(BESCHL_ART) @Value(BESCHL_NR) du @Value(BESCHL_DAT)
    -> FeatureHolder
Terminator_4
    MESSAGE = Translation Terminated
AttributeRemover_6
    REMOVE_ATTRS = EIB_AUSSAGE_FR,AMT_LIEFEREINHEIT,PUN_OID,AMT_OID,EIB_LEGENDESYMBOL_FR,EIB_LIEFEREINHEIT,EIB_AUSSAGE_DE,GGO_ZUSNR,PUN_PUBLIZIERTAB,DAR_LIEFEREINHEIT,EIB_PUBLIZIERTAB,BESCHL_DAT,URL_PLAN,DAR_OID,EIB_OID,URL_BESCHL,BESCHL_NR,BESCHL_ART,EIB_LEGENDESYMBOL_DE,GGO_NAME,GGO_NR
    -> AttributeRenamer_2
AttributeRenamer_2
    ATTR_TABLE = RENAME_SET_DEFAULT VOR_OID > VOR_OIDURSPRUNG
    -> AttributeCreator_6
    -> AttributeCreator_5
Note: VOR_OIDHINWEIS / Naturschutzgesetz
AttributeCreator_5
    ATTR_TABLE = SET_TO VOR_OIDHINWEIS = ch.be.sk.bsg.426.11
    -> UUIDGenerator_5
Note: VOR_OIDHINWEIS Naturschutzverordnung
AttributeCreator_6
    ATTR_TABLE = SET_TO VOR_OIDHINWEIS = ch.be.sk.bsg.426.111
    -> UUIDGenerator_5
Note: HWD_ID
UUIDGenerator_5
    UUID_ATTR = HWD_ID
    -> HINWEIDOK (writer ORACLE_NONSPATIAL_1)
    -> AttributeRenamer_8
Note: OEREB2.HINWEIDOK
HINWEIDOK (writer ORACLE_NONSPATIAL_1)
    attributes: HWD_ID nvarchar(128), HWD_XTF_ID nvarchar(128), HWD_LIEFEREINHEIT number(6,0), HWD_ARTNR nvarchar(255), VOR_OIDURSPRUNG nvarchar(128), VOR_OIDHINWEIS nvarchar(128)
AttributeRenamer_8
    ATTR_TABLE:
      RENAME_SET_DEFAULT HWD_ID > id
      RENAME_SET_DEFAULT VOR_OIDURSPRUNG > document_id
      RENAME_SET_DEFAULT VOR_OIDHINWEIS > reference_document_id
    -> AttributeCreator_15
AttributeCreator_15
    ATTR_TABLE = SET_TO schema = $(schema)
    -> AttributeKeeper_6
AttributeKeeper_6
    KEEP_ATTRS = schema,document_id,reference_document_id,id
    -> document_reference (writer POSTGRES_7)
document_reference (writer POSTGRES_7)
    attributes: id varchar(80),PrimaryKey, document_id varchar(80), reference_document_id varchar(80), article_numbers varchar(80), liefereinheit int4
Terminator_2
    MESSAGE = Translation Terminated
AttributeKeeper
    KEEP_ATTRS = EIB_OID,LAGE_GEN,BESCHL_DAT,AMT_OID
    -> UUIDGenerator_6
Note: VOR_OID
UUIDGenerator_6
    UUID_ATTR = VOR_OID
    -> AttributeFilter
    -> UUIDGenerator_4
Note: HIV_ID
UUIDGenerator_4
    UUID_ATTR = HIV_ID
    -> HINVOR (writer ORACLE_NONSPATIAL_1)
    -> AttributeRenamer_10
AttributeRenamer_10
    ATTR_TABLE:
      RENAME_SET_DEFAULT HIV_ID > id
      RENAME_SET_DEFAULT EIB_OID > public_law_restriction_id
      RENAME_SET_DEFAULT VOR_OID > document_id
    -> AttributeCreator_11
AttributeCreator_11
    ATTR_TABLE = SET_TO schema = $(schema)
    -> AttributeKeeper_4
AttributeKeeper_4
    KEEP_ATTRS = schema,public_law_restriction_id,document_id,id
    -> public_law_restriction_document (writer POSTGRES_8)
public_law_restriction_document (writer POSTGRES_8)
    attributes: id varchar(80),PrimaryKey, public_law_restriction_id varchar(80), document_id varchar(80), article_numbers varchar(80), liefereinheit int4
Note: OEREB2.HINVOR
HINVOR (writer ORACLE_NONSPATIAL_1)
    attributes: HIV_ID nvarchar(128), HIV_XTF_ID nvarchar(128), HIV_ARTNR nvarchar(255), HIV_LIEFEREINHEIT number(6,0), EIB_OID nvarchar(128), VOR_OID nvarchar(128)
Note: Übersetzung "unbekannt" nach FR
AttributeFilter
    ATTR_NAME = LAGE_GEN
    ATTR_VALUES = <Empty>,unbekannt,<Missing>,<Null>,<Unfiltered>
    unbekannt -> AttributeCreator_8
    <UNFILTERED> -> AttributeCreator_9
AttributeCreator_8
    ATTR_TABLE:
      SET_TO VOR_PUBLIZIERTAB = @Value(BESCHL_DAT)
      SET_TO VOR_TITEL_DE = Lagegenauigkeit @Value(LAGE_GEN)
      SET_TO VOR_TITEL_FR = Précision de localisation inconnue
      SET_TO VOR_OFFIZIELLERTITEL_DE = Lagegenauigkeit @Value(LAGE_GEN)
      SET_TO VOR_OFFIZIELLERTITEL_FR = Précision de localisation inconnue
      SET_TO VOA_ID = 3
      SET_TO VOR_TEXTIMWEB_DE =
      SET_TO VOR_TEXTIMWEB_FR =
    -> FeatureHolder
AttributeCreator_9
    ATTR_TABLE:
      SET_TO VOR_PUBLIZIERTAB = @Value(BESCHL_DAT)
      SET_TO VOR_TITEL_DE = Lagegenauigkeit @Value(LAGE_GEN)
      SET_TO VOR_TITEL_FR = Précision de localisation @Value(LAGE_GEN)
      SET_TO VOR_OFFIZIELLERTITEL_DE = Lagegenauigkeit @Value(LAGE_GEN)
      SET_TO VOR_OFFIZIELLERTITEL_FR = Précision de localisation @Value(LAGE_GEN)
      SET_TO VOA_ID = 3
      SET_TO VOR_TEXTIMWEB_DE =
      SET_TO VOR_TEXTIMWEB_FR =
    -> FeatureHolder
FeatureHolder
    -> VORSCHRIFT (writer ORACLE_NONSPATIAL_1)
    -> AttributeRenamer_9
Note: OEREB2.VORSCHRIFT
VORSCHRIFT (writer ORACLE_NONSPATIAL_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)
AttributeRenamer_9
    ATTR_TABLE:
      RENAME_SET_DEFAULT VOR_OID > id
      RENAME_SET_DEFAULT VOR_PUBLIZIERTAB > published_from
      RENAME_SET_DEFAULT AMT_OID > office_id
    -> JSONTemplater_6 [ROOT]
Note: text_at_web-Attribut als JSON-String / aufbauen.
JSONTemplater_6
    RESULT_ATTRIBUTE = text_at_web
    ROOT_QUERY_EXPR:
      {
          "fr": fme:get-attribute("VOR_TEXTIMWEB_FR"),
          "de": fme:get-attribute("VOR_TEXTIMWEB_DE")
      }
    VISIBLE_QUERY_VALIDATE = Yes
    -> AttributeValueMapper_5
Note: document_type-Attribut / mappen
AttributeValueMapper_5
    DIRECTION = Forward (Source To Destination)
    LUT = 1,LegalProvision,2,Law,3,Hint
    SRC = VOA_ID
    VAL_ATTR = document_type
    -> AttributeCreator_13
Note: type-Attribut ist wohl immer "document"
AttributeCreator_13
    ATTR_TABLE = SET_TO type = document
    -> JSONTemplater_3 [ROOT]
Note: Title-Attribut als JSON-String / aufbauen.
JSONTemplater_3
    RESULT_ATTRIBUTE = title
    ROOT_QUERY_EXPR:
      {
          "fr": fme:get-attribute("VOR_TITEL_FR"),
          "de": fme:get-attribute("VOR_TITEL_DE")
      }
    VISIBLE_QUERY_VALIDATE = Yes
    -> AttributeCreator_14
AttributeCreator_14
    ATTR_TABLE:
      SET_TO official_title = @Value(title)
      SET_TO schema = $(schema)
    -> AttributeKeeper_5
AttributeKeeper_5
    KEEP_ATTRS = office_id,text_at_web,official_title,id,title,published_from,type,document_type,schema
    -> document_base (writer POSTGRES_5)
    -> document (writer POSTGRES_6)
document_base (writer POSTGRES_5)
    attributes: id varchar(80),PrimaryKey, text_at_web json, law_status varchar(80), published_from date, type varchar(80), liefereinheit int4
document (writer POSTGRES_6)
    attributes: document_type varchar(80), title json, official_title json, abbreviation json, official_number varchar(80), canton varchar(2), municipality int4, file varchar(80), id varchar(80),PrimaryKey, office_id varchar(80), liefereinheit int4
Note: DAR_LEGENDEIMWEB_DE
StringConcatenator
    ACTION = Create New Attribute
    PARM_LINE = $(LEGEND_BASEURL)@Value(DAR_LEGENDEIMWEB_DE)
    VAL_ATTR = DAR_LEGENDEIMWEB_DE
    -> StringConcatenator_2
Note: DAR_LEGENDEIMWEB_FR
StringConcatenator_2
    ACTION = Create New Attribute
    PARM_LINE = $(LEGEND_BASEURL)@Value(DAR_LEGENDEIMWEB_FR)
    VAL_ATTR = DAR_LEGENDEIMWEB_FR
    -> DARSTELLUNGSDIENST (writer ORACLE_NONSPATIAL_1)
    -> JSONTemplater_4 [ROOT]
Note: OEREB2.DARSTELLUNGSDIENST
DARSTELLUNGSDIENST (writer ORACLE_NONSPATIAL_1)
    attributes: DAR_OID nvarchar(128), DAR_XTF_ID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(6,0)
Note: legend_at_web-Attribut als JSON-String / aufbauen.
JSONTemplater_4
    RESULT_ATTRIBUTE = legend_at_web
    ROOT_QUERY_EXPR:
      {
          "fr": fme:get-attribute("DAR_LEGENDEIMWEB_DE"),
          "de": fme:get-attribute("DAR_LEGENDEIMWEB_FR")
      }
    VISIBLE_QUERY_VALIDATE = Yes
    -> AttributeRenamer_6
AttributeRenamer_6
    ATTR_TABLE:
      RENAME_SET_DEFAULT DAR_OID > id
      RENAME_SET_DEFAULT DAR_VERWEISWMS_DE > reference_wms
    -> view_service (writer POSTGRES_2)
view_service (writer POSTGRES_2)
    attributes: id varchar(80),PrimaryKey, reference_wms varchar(80), legend_at_web jsonb, liefereinheit int4

Bookmark: Aggregation für TypeCode
Aggregator_10
    ACCUM_ATTRS_NAME = Use Attributes From One Feature
    AGGREGATE_TYPE = Homogeneous Collection (If Possible)
    GROUP_BY = information published_from liefereinheit topic sub_theme symbol_url schema view_service_id office_id
    LIST_ATTRS_TO_INCLUDE = plr_id
    LIST_NAME = plr_ids
    MODE = Geometry - Assemble One Level
    ORDERED = No
    SEP = ,
    AGGREGATE -> UUIDGenerator_7
UUIDGenerator_7
    UUID_ATTR = legend_entry_id
    -> UUIDGenerator_8
UUIDGenerator_8
    UUID_ATTR = type_code
    -> UUIDGenerator_9
UUIDGenerator_9
    UUID_ATTR = type_code_list
    -> AttributeManager
    -> AttributeRenamer_12
AttributeManager
    ATTR_TABLE:
      REMOVE symbol_url
      REMOVE plr_id
      REMOVE legend_entry_id
    -> ListExploder
ListExploder
    ATTR_ACCUM_MODE = Merge List Attributes
    ATTR_CONFLICT_RES = Use List Attribute Values
    INDEX_ATTR = _element_index
    LIST_ATTR = plr_ids{}
    ELEMENTS -> AttributeRenamer_14
AttributeRenamer_14
    ATTR_TABLE = RENAME_SET_DEFAULT plr_id > id
    -> public_law_restriction (writer POSTGRES_3)
AttributeRenamer_12
    ATTR_TABLE = RENAME_SET_DEFAULT information > legend_text
    -> AttributeKeeper_11
AttributeKeeper_11
    KEEP_ATTRS = legend_text,schema,topic,symbol_url,sub_theme,view_service_id,legend_entry_id,type_code,liefereinheit,type_code_list
    -> AttributeRenamer_13
    -> AttributeKeeper_9
AttributeRenamer_13
    ATTR_TABLE = RENAME_SET_DEFAULT legend_entry_id > id
    -> FeatureMerger_3 [REQUESTOR]
AttributeKeeper_9
    KEEP_ATTRS = symbol_url
    -> Aggregator_3
Aggregator_3
    ACCUM_ATTRS_NAME = Use Attributes From One Feature
    AGGREGATE_TYPE = Homogeneous Collection (If Possible)
    GROUP_BY = symbol_url
    MODE = Geometry - Assemble One Level
    ORDERED = No
    SEP = ,
    AGGREGATE -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = symbol_binary
    TARGET_ATTR_ENCODING = auto-detect
    TARGET_URL = @Value(symbol_url)
    TRANSFER_TIMEOUT_LENGTH = 90
    USE_COOKIES = No
    VERIFY_SSL_CERTIFICATES = Yes
    -> BinaryEncoder_2
BinaryEncoder_2
    ATTR_TO_ENCODE = symbol_binary
    DEST_ATTR = symbol
    ENCODING_TYPE = Base64
    -> AttributeKeeper_10
AttributeKeeper_10
    KEEP_ATTRS = symbol_url,symbol
    -> FeatureMerger_3 [SUPPLIER]
FeatureMerger_3
    ATTR_ACCUM_MODE = Merge Supplier
    ATTR_CONFLICT_RES = Use Requestor
    IGNORE_NULLS = No
    JOIN_KEYS = @Value(symbol_url) @Value(symbol_url) AUTO
    MERGE_TYPE = Attributes Only
    PROCESS_DUPS = NO
    REJECT_NULL_MISSING_KEYS = No
    SUPPLIERS_FIRST = No
    MERGED -> AttributeKeeper_7
AttributeKeeper_7
    KEEP_ATTRS = schema,sub_theme,type_code,id,topic,type_code_list,liefereinheit,legend_text,symbol_url,symbol,view_service_id
    -> legend_entry (writer POSTGRES_4)
