FME workspace s22_import_prjzflug.fmw
Startup Python:
      # -*- coding: utf-8 -*-
      import fmeobjects

      #=======================================================================================
      # Mehrsprachige Felder in INTERLIS2 behandeln
      def processMultilangFields(feature):

          multilangFields = feature.getAttribute('multilangfields').split(",")

          for mlField in multilangFields:
              content_de = ""
              content_fr = ""
              content_it = ""

              att_Language_list = feature.getAttribute(mlField + '{0}.LocalisedText{}.Language')
              att_Text_list = feature.getAttribute(mlField + '{0}.LocalisedText{}.Text')

              # wenn das Multilang-Feld nicht abgefüllt ist, soll es nicht bearbeitet werden
              if att_Language_list is not None:

                      for i in range(len(att_Language_list)):
                          if att_Language_list[i]=="de":
                              content_de = att_Text_list[i]
                          if att_Language_list[i]=="fr":
                              content_fr = att_Text_list[i]
                          if att_Language_list[i]=="it":
                              content_it = att_Text_list[i]

                      # Wenn der Text nur in einer Sprache vorhanden ist, wird er auch für die andere Sprache verwendet
                      if content_de == "":
                          content_de = content_fr
                      if content_de == "":
                          content_de = content_it
                      if content_fr == "":
                          content_fr = content_de
                      if content_fr == "":
                          content_fr = content_it

              feature.setAttribute(mlField + "_DE", content_de)
              feature.setAttribute(mlField + "_FR", content_fr)

Parameters:
- XTF_FILE =   # XTF-File
- DATABASE =   # Database
- USERNAME =   # Username
- PASSWORD =   # PASSWORD Password
- MODELLABLAGE =   # Modellablage
- LOGFILE =   # Logfile
- GEODB_PG_DATABASE =
- GEODB_PG_USERNAME =
- GEODB_PG_PASSWORD =
- GEODB_PG_HOST =
- GEODB_PG_PORT =

Readers:
- ch.ehi.fme.Main_2: ch.ehi.fme.Main from $(XTF_FILE) in $(XTF_FILE)

Writers:
- GEODATABASE_SDE_1: GEODATABASE_SDE to sde
- POSTGIS_1: POSTGIS to $(GEODB_PG_DATABASE)

Note: ReservedZones_WithLatestModification.Geometry
ReservedZonesForAirportInstallations_LV95_V2_3.ReservedZones_WithLatestModification.Geometry (reader ch.ehi.fme.Main_2)
    attributes: xtf_id xtf_char(200), Kind{}.xtf_class xtf_char(109), Kind{}.Reference xtf_char(200), Modification{}.xtf_class xtf_char(109), Modification{}.ValidFrom xtf_datetime, Modification{}.ValidUntil xtf_datetime, Modification{}.LatestModification xtf_datetime, Modification{}.Modifications{}.xtf_class xtf_char(109), Modification{}.Modifications{}.Reference xtf_char(200), Zone xtf_char(200)
    -> CoordinateSystemSetter
CoordinateSystemSetter
    COORDSYS = EPSG:2056
    -> AttributeRemover
AttributeRemover
    LIST_ATTRS = Kind{}.Reference Kind{} Modification{}.LatestModification Modification{}.Modifications{} Kind{}.Ref Modification{} Modification{}.Modifications{}.Reference Kind{}.xtf_class Modification{}.ValidFrom Modification{}.ValidUntil Modification{}.xtf_class Modification{}.Modifications{}.xtf_class
    REMOVE_ATTRS = xtf_id
    -> FeatureMerger [REQUESTOR]
Note: ReservedZones_WithLatestModification.ReservedZone
ReservedZonesForAirportInstallations_LV95_V2_3.ReservedZones_WithLatestModification.ReservedZone (reader ch.ehi.fme.Main_2)
    attributes: xtf_id xtf_char(200), Identifier xtf_char(30), Name{}.xtf_class xtf_char(109), Name{}.LocalisedText{}.xtf_class xtf_char(109), Name{}.LocalisedText{}.Language xtf_char(255), Name{}.LocalisedText{}.Text xtf_buffer, Status{}.xtf_class xtf_char(109), Status{}.Reference xtf_char(200), Applicant xtf_buffer, Canton xtf_char(255), Municipality xtf_buffer, DurationOfEffect xtf_int32, Validity{}.xtf_class xtf_char(109), Validity{}.ValidFrom xtf_datetime, Validity{}.ValidUntil xtf_datetime, Validity{}.LatestModification xtf_datetime, Validity{}.Modifications{}.xtf_class xtf_char(109), Validity{}.Modifications{}.Reference xtf_char(200), Description{}.xtf_class xtf_char(109), Description{}.LocalisedText{}.xtf_class xtf_char(109), Description{}.LocalisedText{}.Language xtf_char(255), Description{}.LocalisedText{}.Text xtf_buffer
    -> AttributeCreator
Note: STATUS extrahieren
AttributeValueMapper_2
    DIRECTION = Forward (Source To Destination)
    LUT = 103-S-01,1,103-S-02,2
    SRC = Status{0}.Reference
    VAL_ATTR = STATUS
    -> AttributeRemover_2
AttributeRemover_2
    LIST_ATTRS = Name{} Description{}.LocalisedText{}.xtf_class Validity{}.Modifications{}.xtf_class Name{}.LocalisedText{} Validity{}.Modifications{}.Reference Name{}.LocalisedText{}.Text Name{}.LocalisedText{}.xtf_class Description{} Name{}.xtf_class Validity{}.LatestModification Description{}.LocalisedText{}.Text Validity{} Description{}.LocalisedText{} Validity{}.ValidUntil Name{}.LocalisedText{}.Language Validity{}.ValidFrom Validity{}.Modifications{} Description{}.xtf_class Status{}.Reference Validity{}.xtf_class Description{}.LocalisedText{}.Language Status{} Status{}.xtf_class Status{}.Ref
    REMOVE_ATTRS = multilangfields,Name_FR,status_xtf_class,status_Ref,status_Reference
    -> AttributeRenamer
AttributeRenamer
    ATTR_LIST = Applicant,ANTRAGST,"",Canton,KANTON,"",Municipality,GEMEINDE,"",DurationOfEffect,DAUER,"",Name_DE,NAME,"",Description_DE,BESCHR_D,"",Description_FR,BESCHR_F,"",Identifier,ZONENID,""
    -> FeatureMerger [SUPPLIER]
    -> AttributeRemover_4
FeatureMerger
    IGNORE_NULLS = Yes
    JOIN_KEYS = @Value(Zone) @Value(xtf_id) AUTO
    MERGE_TYPE = Attributes Only
    PROCESS_DUPS = No
    SUPPLIERS_FIRST = No
    SUPPLIER_PREFIX_DUMMY = YES
    MERGED -> BulkAttributeRenamer
    MERGED -> PRJZFLUG_PRJZFLUG (writer GEODATABASE_SDE_1)
Note: GEODB.PRJZFLUG_PRJZFLUG
PRJZFLUG_PRJZFLUG (writer GEODATABASE_SDE_1)
    attributes: ZONENID char(30), ANTRAGST char(255), KANTON char(2), GEMEINDE char(1024), NAME char(255), STATUS smallint, DAUER smallint, BESCHR_D char(1024), BESCHR_F char(1024)
BulkAttributeRenamer
    ATTRCHOICE = All Attributes
    CASE_CHANGE_TYPE = lower
    MODE_CHOICE = RENAME
    PATTERN_ACTION_DISP = CASECHANGE
    -> prjzflug_prjzflug (writer POSTGIS_1)
prjzflug_prjzflug (writer POSTGIS_1)
    attributes: objectid int4, zonenid varchar(30), antragst varchar(255), kanton varchar(2), gemeinde varchar(1024), name varchar(255), status int2, dauer int2, beschr_d varchar(1024), beschr_f varchar(1024)
AttributeRemover_4
    REMOVE_ATTRS = ANTRAGST,KANTON,GEMEINDE,DAUER,NAME,BESCHR_D,BESCHR_F,STATUS
    -> FeatureMerger_2 [REQUESTOR]
Note: RelatedDocuments_WithLatestModification.Document
ReservedZonesForAirportInstallations_LV95_V2_3.RelatedDocuments_WithLatestModification.Document (reader ch.ehi.fme.Main_2)
    attributes: xtf_id xtf_char(200), Title xtf_buffer, Weblink xtf_char(1023), Language xtf_char(255), Modification{}.xtf_class xtf_char(109), Modification{}.ValidFrom xtf_datetime, Modification{}.ValidUntil xtf_datetime, Modification{}.LatestModification xtf_datetime, Modification{}.Modifications{}.xtf_class xtf_char(109), Modification{}.Modifications{}.Reference xtf_char(200), Description{}.xtf_class xtf_char(109), Description{}.LocalisedText{}.xtf_class xtf_char(109), Description{}.LocalisedText{}.Language xtf_char(255), Description{}.LocalisedText{}.Text xtf_buffer
    -> AttributeCreator_4
AttributeRemover_5
    LIST_ATTRS = Description{}.LocalisedText{} Modification{}.LatestModification Modification{}.Modifications{} Modification{} Modification{}.Modifications{}.Reference Description{} Description{}.LocalisedText{}.Language Modification{}.ValidFrom Description{}.LocalisedText{}.Text Description{}.xtf_class Modification{}.ValidUntil Modification{}.xtf_class Modification{}.Modifications{}.xtf_class Description{}.LocalisedText{}.xtf_class
    REMOVE_ATTRS = Language,multilangfields,Description_FR
    -> AttributeRenamer_4
AttributeRenamer_4
    ATTR_LIST = Title,TITEL,"",Weblink,WEBLINK,"",Description_DE,BESCHRIEB,"",xtf_id,doku_xtf_id,""
    -> FeatureMerger_3 [REQUESTOR]
Note: RelatedDocuments_WithLatestModification.OriginReference
ReservedZonesForAirportInstallations_LV95_V2_3.RelatedDocuments_WithLatestModification.OriginReference (reader ch.ehi.fme.Main_2)
    attributes: xtf_id xtf_char(200), Origin xtf_char(200), Reference xtf_char(200)
    -> AttributeRemover_7
AttributeRemover_7
    REMOVE_ATTRS = xtf_id
    -> FeatureMerger_3 [SUPPLIER]
FeatureMerger_3
    ATTR_ACCUM_MODE = Merge Supplier
    ATTR_CONFLICT_RES = Use Requestor
    IGNORE_NULLS = No
    JOIN_KEYS = @Value(doku_xtf_id) @Value(Reference) AUTO
    MERGE_TYPE = Attributes Only
    PROCESS_DUPS = NO
    REJECT_NULL_MISSING_KEYS = No
    SUPPLIERS_FIRST = No
    MERGED -> AttributeManager
    UNMERGED_REQUESTOR -> FeatureMerger_4 [SUPPLIER]
AttributeManager
    ATTR_TABLE:
      REMOVE doku_xtf_id
      RENAME_SET_VALUE Origin > doku_xtf_id
      REMOVE Reference
    -> FeatureMerger_4 [SUPPLIER]
Note: ReservedZones_WithLatestModification.ReservedZonePrescription
ReservedZonesForAirportInstallations_LV95_V2_3.ReservedZones_WithLatestModification.ReservedZonePrescription (reader ch.ehi.fme.Main_2)
    attributes: xtf_id xtf_char(200), Prescription xtf_char(200), Restriction xtf_char(200)
    -> AttributeRemover_3
AttributeRemover_3
    REMOVE_ATTRS = xtf_id
    -> FeatureMerger_4 [REQUESTOR]
FeatureMerger_4
    ATTR_ACCUM_MODE = Merge Supplier
    ATTR_CONFLICT_RES = Use Requestor
    CLEANING_TOLERANCE = None
    CONNECT_Z_MODE = First Wins
    GEOM_TYPE = Build Polygons
    IGNORE_NULLS = Yes
    JOIN_KEYS = @Value(Prescription) @Value(doku_xtf_id) AUTO
    LIST_NAME = regulations
    MERGE_TYPE = Attributes Only
    PROCESS_DUPS = YES
    REJECT_NULL_MISSING_KEYS = No
    SUPPLIERS_FIRST = No
    MERGED -> FeatureMerger_2 [SUPPLIER]
FeatureMerger_2
    ATTR_ACCUM_MODE = Merge Supplier
    ATTR_CONFLICT_RES = Use Requestor
    IGNORE_NULLS = Yes
    JOIN_KEYS = @Value(xtf_id) @Value(Restriction) AUTO
    MERGE_TYPE = Attributes Only
    PROCESS_DUPS = NO
    REJECT_NULL_MISSING_KEYS = No
    SUPPLIERS_FIRST = No
    MERGED -> AttributeRemover_6
AttributeRemover_6
    REMOVE_ATTRS = TITEL,WEBLINK,BESCHRIEB
    -> ListExploder
ListExploder
    INDEX_ATTR = _element_index
    LIST_ATTR = regulations{}
    MODE = List Elements and Original Attributes
    LIST_FOUND -> AttributeRemover_10
AttributeRemover_10
    REMOVE_ATTRS = xtf_id,Prescription,Restricition,doku_xtf_id,_element_index
    -> PRJZFLUG_REVO (writer GEODATABASE_SDE_1)
    -> BulkAttributeRenamer_2
BulkAttributeRenamer_2
    ATTRCHOICE = All Attributes
    CASE_CHANGE_TYPE = lower
    MODE_CHOICE = RENAME
    PATTERN_ACTION_DISP = CASECHANGE
    -> prjzflug_revo (writer POSTGIS_1)
prjzflug_revo (writer POSTGIS_1)
    attributes: objectid int4, zonenid varchar(30), titel varchar(255), weblink varchar(1024), beschrieb varchar(1024)
PRJZFLUG_REVO (writer GEODATABASE_SDE_1)
    attributes: ZONENID char(30), TITEL char(255), WEBLINK char(1024), BESCHRIEB char(1024)

Bookmark: Mehrsprachige Felder bearbeiten
AttributeCreator
    ATTR_LIST = multilangfields,Name
    -> PythonCaller
PythonCaller
    NEW_ATTRIBUTES = Name_DE Name_FR
    PYTHONSYMBOL = processMultilangFields
    -> AttributeCreator_2
AttributeCreator_2
    ATTR_LIST = multilangfields,Description
    -> PythonCaller_2
PythonCaller_2
    NEW_ATTRIBUTES = Description_DE Description_FR
    PYTHONSYMBOL = processMultilangFields
    -> AttributeValueMapper_2

Bookmark: Mehrsprachige Felder bearbeiten
AttributeCreator_4
    ATTR_LIST = multilangfields,Description
    -> PythonCaller_4
PythonCaller_4
    NEW_ATTRIBUTES = Description_DE Description_FR
    PYTHONSYMBOL = processMultilangFields
    -> AttributeRemover_5
