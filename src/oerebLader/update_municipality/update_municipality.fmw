FME workspace update_municipality.fmw

Parameters:
- LOGO_BASE_PATH =
- SOURCETABLE =
- VEK1_CONNECTIONFILE =
- OEREB_PG_HOST =
- OEREB_PG_PORT =
- OEREB_PG_DB =
- OEREB_PG_USERNAME =
- OEREB_PG_PASSWORD =
- LOGFILE =

Writers:
- POSTGIS_1: POSTGIS to $(OEREB_PG_DB)

Creator
    GEOMTYPE = Geometry Object
    NUM = 1
    CREATED -> FeatureReader [INITIATOR]
FeatureReader
    ATTR_ACCUM_MODE = Only Use Result
    COMBINE_GEOM = Use Result
    FEATURETYPES = $(SOURCETABLE)
    FORMAT = GEODATABASE_SDE
    GEODATABASE_SDE_ALIAS_MODE = NONE
    GEODATABASE_SDE_CACHE_MULTIPATCH_TEXTURES = yes
    GEODATABASE_SDE_CHECK_SIMPLE_GEOM = no
    GEODATABASE_SDE_CONNECTION_FILE = $(VEK1_CONNECTIONFILE)
    GEODATABASE_SDE_CREDENTIALS_OVERRIDE = NO
    GEODATABASE_SDE_FEATURE_READ_MODE = Features
    GEODATABASE_SDE_IGNORE_NETWORK_INFO = yes
    GEODATABASE_SDE_IGNORE_RELATIONSHIP_INFO = yes
    GEODATABASE_SDE_MERGE_FEAT_LINKED_ANNOS = no
    GEODATABASE_SDE_PERSISTENT_CONNECTION = no
    GEODATABASE_SDE_QUERY_FEATURE_TYPES_FOR_MERGE_FILTERS = Yes
    GEODATABASE_SDE_READ_VERSION_DIFFERENCES = NO
    GEODATABASE_SDE_REMOVE_TABLE_QUALIFIER = NO
    GEODATABASE_SDE_RESOLVE_DOMAINS = no
    GEODATABASE_SDE_RESOLVE_SUBTYPE_NAMES = yes
    GEODATABASE_SDE_SPLIT_COMPLEX_ANNOS = no
    GEODATABASE_SDE_SPLIT_COMPLEX_EDGES = no
    GEODATABASE_SDE_SPLIT_MULTI_PART_ANNOS = no
    GEODATABASE_SDE_TRANSLATE_SPATIAL_DATA_ONLY = no
    GEODATABASE_SDE_USE_SEARCH_ENVELOPE = NO
    GEODATABASE_SDE_VERSION_TYPE = Version from SDE Connection
    INTERACT = <No Spatial Filter>
    OUTPUT_FEATURES_DISPLAY = Schema and Data Features
    WHERE = SEE=0 AND KT=2
    <OTHER> -> AttributeExposer
AttributeExposer
    ATTR_LIST = BFSNR,GEMNAME
    -> AttributeRenamer
AttributeRenamer
    ATTR_TABLE:
      RENAME_SET_DEFAULT GEMNAME > name
      RENAME_SET_DEFAULT BFSNR > fosnr
    -> AggregateFilter
AggregateFilter
    AGGREGATE -> AttributeCreator
    NOT_AGGREGATE -> Aggregator
Aggregator
    ACCUM_ATTRS_NAME = Use Attributes From One Feature
    AGGREGATE_TYPE = Homogeneous Collection (If Possible)
    GROUP_BY = fosnr name
    MODE = Geometry - Assemble One Level
    ORDERED = No
    SEP = ,
    AGGREGATE -> AttributeCreator
AttributeCreator
    ATTR_TABLE = SET_TO published = true
    -> StringConcatenator
StringConcatenator
    ACTION = Create New Attribute
    PARM_LINE = $(LOGO_BASE_PATH)@Value(fosnr).png
    VAL_ATTR = logo_url
    -> HTTPCaller
HTTPCaller
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = logo_binary
    TARGET_ATTR_ENCODING = auto-detect
    TARGET_URL = @Value(logo_url)
    TRANSFER_TIMEOUT_LENGTH = 90
    USE_COOKIES = No
    VERIFY_SSL_CERTIFICATES = Yes
    -> BinaryEncoder
    <Rejected> -> Logger
Logger
    LOG_FEATURE = LOG_ONLY
    MAXCOORDS = 20
    MAXFEATS = 20
    MESSAGE = Fehlendes Gemeindelogo:
    SEVERITY = WARN
    LOGGED -> StringConcatenator_2
Note: Gemeinden ohne Logos
StringConcatenator_2
    ACTION = Create New Attribute
    PARM_LINE = $(LOGO_BASE_PATH)logo_print_kanton.png
    VAL_ATTR = logo_url
    -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = logo_binary
    TARGET_ATTR_ENCODING = auto-detect
    TARGET_URL = @Value(logo_url)
    TRANSFER_TIMEOUT_LENGTH = 90
    USE_COOKIES = No
    VERIFY_SSL_CERTIFICATES = Yes
    -> BinaryEncoder
BinaryEncoder
    ATTR_TO_ENCODE = logo_binary
    DEST_ATTR = logo
    ENCODING_TYPE = Base64
    -> AttributeKeeper
AttributeKeeper
    KEEP_ATTRS = name,logo,published,fosnr
    -> CoordinateRounder_2
CoordinateRounder_2
    XPREC = 3
    YPREC = 3
    ZPREC = 0
    ROUNDED -> municipality (writer POSTGIS_1)
municipality (writer POSTGIS_1)
    attributes: fosnr int4,PrimaryKey, name varchar(80), published bool, logo varchar(80)
