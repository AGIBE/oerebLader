FME workspace s11_derive_nplwald_transfer.fmw

Parameters:
- GEODB_DATABASE =   # GeoDB-Database
- GEODB_USERNAME =   # GEODB-Username
- GEODB_PASSWORD =   # GEODB-Passwort
- LOGFILE =   # Logfile
- BFSNR =   # BFS-Nr
- LIEFEREINHEIT =   # Liefereinheit
- OEREB_DATABASE =   # OEREB-Database
- OEREB_USERNAME =   # OEREB-Username
- OEREB_PASSWORD =   # OEREB-Passwort

Readers:
- GEODATABASE_SDE_1: GEODATABASE_SDE from sde

Writers:
- GEODATABASE_SDE_2: GEODATABASE_SDE to sde
- ORACLE8I_DB_1: ORACLE8I_DB to $(OEREB_DATABASE)

Note: GEODB.NPLWALD_WAFW
GEODB.NPLWALD_WAFW (reader GEODATABASE_SDE_1)
    attributes: BFSNR smallint, REL_ID char(100)
    -> AttributeRenamer_15
AttributeRenamer_15
    ATTR_LIST = REL_ID,EIB_OID,""
    -> AttributeCreator_16
AttributeCreator_16
    ATTR_LIST = RES_ID,1,DAR_OID,GEODB.NPLWALD_WAFW,THE_ID,16,EIB_AUSSAGE_DE,Verbindlich festgelegte Waldgrenze,EIB_SORT,100
    -> UUIDGenerator
Note: FLA_OID als UUID
UUIDGenerator
    UUID_ATTR = FLA_OID
    -> TimeStamper
Note: publiziertAb (heute)
TimeStamper
    FMT = FME Date (^Y^m^d)
    TIME_ATTR = FLA_PUBLIZIERTAB
    -> AttributeCreator
Note: Attribute erstellen
AttributeCreator
    ATTR_LIST = EIB_AUSSAGE_FR,@Value(EIB_AUSSAGE_DE),EIB_PUBLIZIERTAB,@Value(FLA_PUBLIZIERTAB),RES_ID,1,FLA_LIEFEREINHEIT,$(LIEFEREINHEIT),EIB_LIEFEREINHEIT,$(LIEFEREINHEIT),AMT_OID,ch.be.vol.kawa,LIN_OID,@Value(FLA_OID),LIN_PUBLIZIERTAB,@Value(FLA_PUBLIZIERTAB),LIN_LIEFEREINHEIT,$(LIEFEREINHEIT),PUN_OID,@Value(FLA_OID),PUN_PUBLIZIERTAB,@Value(FLA_PUBLIZIERTAB),PUN_LIEFEREINHEIT,$(LIEFEREINHEIT)
    -> AttributeRemover
    -> GeometryFilter
GeometryFilter
    BREAK_AGG = No
    LINE -> OEREB.LINIE (writer GEODATABASE_SDE_2)
    ARC -> OEREB.LINIE (writer GEODATABASE_SDE_2)
Note: OEREB.LINIE
OEREB.LINIE (writer GEODATABASE_SDE_2)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
AttributeRemover
    REMOVE_ATTRS = BFSNR,FLA_OID,FLA_PUBLIZIERTAB,FLA_LIEFEREINHEIT,LIN_OID,LIN_PUBLIZIERTAB,LIN_LIEFEREINHEIT,PUN_OID,PUN_PUBLIZIERTAB,PUN_LIEFEREINHEIT
    -> Aggregator
Note: Gruppieren nach Eigentums- / beschraenkung
Aggregator
    GROUP_BY = EIB_OID RES_ID DAR_OID THE_ID EIB_AUSSAGE_DE EIB_SORT EIB_AUSSAGE_FR EIB_PUBLIZIERTAB EIB_LIEFEREINHEIT AMT_OID
    MODE = Assemble One Level
    ACCUM_ATTRS_NAME = No
    SEP = ,
    AGGREGATE_TYPE = Homogeneous Collection (If Possible)
    ORDERED = No
    AGGREGATE -> OEREB.EIGENTUMSBESCHRAENKUNG (writer ORACLE8I_DB_1)
    AGGREGATE -> AttributeRemover_2
Note: OEREB.EIGENTUMSBESCHRAENKUNG
OEREB.EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), THE_ID number(10,0), EIB_SORT number(10,0)
AttributeRemover_2
    REMOVE_ATTRS = RES_ID,DAR_OID,THE_ID,EIB_AUSSAGE_DE,EIB_SORT,EIB_AUSSAGE_FR,EIB_PUBLIZIERTAB,EIB_LIEFEREINHEIT,AMT_OID
    -> FeatureMerger [input 2]
Note: GEODB.NPLWALD_FWRVT
GEODB.NPLWALD_FWRVT (reader GEODATABASE_SDE_1)
    attributes: BFSNR smallint, RELID char(100), ARTIKELNR char(40), ART char(50), TEXTIMWEB char(200), TITEL char(200), OFFIZTITEL char(200), ABKUERZUNG char(10), OFFIZNR char(20), geodb_oid integer, OBJECTID integer, NAME char(31)
    -> UUIDGenerator_2
Note: VOR_OID als UUID
UUIDGenerator_2
    UUID_ATTR = VOR_OID
    -> TimeStamper_2
Note: publiziertAb (heute)
TimeStamper_2
    FMT = FME Date (^Y^m^d)
    TIME_ATTR = VOR_PUBLIZIERTAB
    -> UUIDGenerator_3
UUIDGenerator_3
    UUID_ATTR = HIV_ID
    -> AttributeRenamer_2
Note: Attribute umbenennen
AttributeRenamer_2
    ATTR_LIST = ABKUERZUNG,VOR_ABKUERZUNG_DE,"",ARTIKELNR,HIV_ARTNR,"",OFFIZNR,VOR_OFFIZIELLENR,"",OFFIZTITEL,VOR_OFFIZIELLERTITEL_DE,"",TEXTIMWEB,VOR_TEXTIMWEB_DE,"",TITEL,VOR_TITEL_DE,"",RELID,EIB_OID,""
    -> AttributeCreator_2
Note: Attribute erstellen
AttributeCreator_2
    ATTR_LIST = VOR_TEXTIMWEB_FR,@Value(VOR_TEXTIMWEB_DE),VOR_TITEL_FR,@Value(VOR_TITEL_DE),VOR_OFFIZIELLERTITEL_FR,@Value(VOR_OFFIZIELLERTITEL_DE),VOR_ABKUERZUNG_FR,@Value(VOR_ABKUERZUNG_DE),RES_ID,1,AMT_OID,ch.be.vol.kawa,VOR_LIEFEREINHEIT,$(LIEFEREINHEIT),HIV_LIEFEREINHEIT,$(LIEFEREINHEIT)
    -> AttributeValueMapper
Note: Dokumenttyp mappen
AttributeValueMapper
    DIRECTION = Forward (Source To Destination)
    VAL_ATTR = VOA_ID
    LUT = Rechtsvorschrift,1,Gesetzliche Grundlage,2,Hinweis,3
    SRC = ART
    -> FeatureMerger [input 1]
FeatureMerger
    PROCESS_DUPS = No
    MERGE_TYPE = Attributes Only
    SUPPLIERS_FIRST = No
    JOIN_KEYS = @Value(EIB_OID) @Value(EIB_OID)
    MERGED -> OEREB.HINVOR (writer ORACLE8I_DB_1)
    MERGED -> OEREB.VORSCHRIFT (writer ORACLE8I_DB_1)
Note: OEREB.HINVOR
OEREB.HINVOR (writer ORACLE8I_DB_1)
    attributes: HIV_ID nvarchar(128), HIV_XTF_ID nvarchar(128), HIV_ARTNR nvarchar(255), HIV_LIEFEREINHEIT number(5,0), EIB_OID nvarchar(128), VOR_OID nvarchar(128)
Note: OEREB.VORSCHRIFT
OEREB.VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(5,0), RES_ID number(10,0), BFS_NR number(5,0), VOA_ID number(10,0), AMT_OID nvarchar(128), DOKUMENT blob
