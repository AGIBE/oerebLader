FME workspace s48_import_nupla.fmw

Parameters:
- ITF_FILE =   # Interlis-Datei
- MODELLABLAGE =   # Modellablage
- OEREB2_DATABASE =   # Oereb2-Database
- OEREB2_USERNAME =   # Oereb2-Username
- OEREB2_PASSWORD =   # Oereb2-Passwort
- GEODB_DATABASE =   # GeoDB-Database
- GEODB_USERNAME =   # GeoDB-Username
- GEODB_PASSWORD =   # GeoDB-Passwort
- BFSNR =   # BFS-Nummer
- GEMNAME =   # Gemeindename
- LOGFILE =   # Logfile
- LIEFEREINHEIT =   # Liefereinheit
- EXCEL_AMT =   # Excel-File AMT
- INPUT_RV_DIR =   # Input-Verzeichnis RV
- OUTPUT_RV_DIR =   # Output-Verzeichnis RV
- OUTPUT_RV_URL =   # Output-Url RV
- SIMPLIFY_GEOMETRY =   # Simplify Geometry
- CREATE_LINETABLES =   # Create Linetables
- GEODB_PG_DATABASE =   # GeoDB-PG-Database
- GEODB_PG_PASSWORD =
- GEODB_PG_USERNAME =
- GEODB_PG_HOST =
- GEODB_PG_PORT =   # GEODB_PG_HOST
- OEREB_PG_DATABASE =
- OEREB_PG_HOST =
- OEREB_PG_PASSWORD =
- OEREB_PG_PORT =
- OEREB_PG_USERNAME =
- STROKER =
- NPL_WMS_BASE =   # WMS-Basis-URL
- AMT_OID =
- law_status = inForce
- NPL_TOPIC = LandUsePlans
- LAERM_TOPIC = NoiseSensitivityLevels
- WALDABST_TOPIC = ForestDistanceLines
- LAERM_SCHEMA = noise_sensitivity_levels
- WALDABST_SCHEMA = forest_distance_lines
- NPL_SCHEMA = land_use_plans
- topic = ContaminatedSites

Readers:
- ch.ehi.fme.Main_1: ch.ehi.fme.Main from $(ITF_FILE) in EPSG:2056
- XLSXR_1: XLSXR from $(EXCEL_AMT)

Writers:
- ORACLE8I_DB_1: ORACLE8I_DB to $(OEREB2_DATABASE)
- GEODATABASE_SDE_1: GEODATABASE_SDE to sde
- GEODATABASE_SDE_2: GEODATABASE_SDE to sde
- FILECOPY_1: FILECOPY to C:\Windows\Temp
- POSTGIS_1: POSTGIS to $(GEODB_PG_DATABASE) in EPSG:2056
- POSTGRES_1: POSTGRES to $(OEREB_PG_DATABASE)
- POSTGRES_2: POSTGRES to $(OEREB_PG_DATABASE)
- POSTGRES_3: POSTGRES to $(OEREB_PG_DATABASE)
- POSTGRES_4: POSTGRES to $(OEREB_PG_DATABASE)
- POSTGIS_2: POSTGIS to $(OEREB_PG_DATABASE)
- POSTGRES_5: POSTGRES to $(OEREB_PG_DATABASE)
- POSTGRES_6: POSTGRES to $(OEREB_PG_DATABASE)
- POSTGRES_7: POSTGRES to $(OEREB_PG_DATABASE)
- POSTGRES_8: POSTGRES to $(OEREB_PG_DATABASE)

Note: Amt vorbereiten
Amt_vorbereiten: Amt vorbereiten
    AMTIMWEB = @Value(AmtImWeb)
    NAME = @Value(Name)
    UID_AMT = @Value(UID_Amt)
    XTF_ID = @Value(xtf_id)
    AMT -> Dokument_vorbereiten [Amt]
    AMT -> FeatureMerger_3 [REQUESTOR]
    AMT -> FeatureMerger_4 [REQUESTOR]
    AMT -> GN_Grundnutzung [Alle_Aemter]
    AMT -> UE_Ueberlagerung [Alle_Aemter]
    AMT -> UE_Abstandslinie [Alle_Aemter]
    AMT -> NH_NaturHeimatSchutz [Alle_Aemter]
    AMT -> WE_WegRoute [Alle_Aemter]
    AMT -> GW_Gewaesser [Alle_Aemter]
    AMT -> GR_Gewaesserraum [Alle_Aemter]
    AMT -> VE_Vor_Einschraenkung [AlleAemter]
Note: NUPLA_GNZPPUEO
NUPLA_GNZPPUEO (writer GEODATABASE_SDE_2)
    attributes: BFSNR smallint, GEMNAME char(50), RVS_ID char(100), GENEHM date, INKRAFT date, BESCHRIEB char(80), QUALITAET smallint, VERBINDLKT smallint, KANTART char(10), ZONENABK char(12), BEZ char(150), PLANBESCHR char(150), BEMERK char(80), DARST_C char(5), DATENVERW char(36), ZUSTAENDIG char(36), BUNDESART char(10), NZ float, NZ_ART smallint, GRUENFZ float, LAERMES smallint, FLMASS integer, BR_NUTZART char(80), BR_NMASS char(80)
BulkAttributeRenamer_3
    ATTRCHOICE = All Attributes
    CASE_CHANGE_TYPE = lower
    MODE_CHOICE = RENAME
    PATTERN_ACTION_DISP = CASECHANGE
    -> nupla_gnzppueo (writer POSTGIS_1)
Note: geodb.nupla_gnzppueo
nupla_gnzppueo (writer POSTGIS_1)
    attributes: bfsnr int2, gemname varchar(50), rvs_id varchar(100), genehm timestamp, inkraft timestamp, beschrieb varchar(80), qualitaet int2, verbindlkt int2, kantart varchar(10), zonenabk varchar(12), bez varchar(150), planbeschr varchar(150), bemerk varchar(80), darst_c varchar(5), datenverw varchar(36), zustaendig varchar(36), bundesart varchar(10), nz float4, nz_art int2, gruenfz float4, laermes int2, flmass int4, br_nutzart varchar(80), br_nmass varchar(80)
BulkAttributeRenamer_2
    ATTRCHOICE = All Attributes
    CASE_CHANGE_TYPE = lower
    MODE_CHOICE = RENAME
    PATTERN_ACTION_DISP = CASECHANGE
    -> nupla_gngruzo (writer POSTGIS_1)
Note: geodb.nupla_gngruzo
nupla_gngruzo (writer POSTGIS_1)
    attributes: bfsnr int2, gemname varchar(50), rvs_id varchar(100), genehm timestamp, inkraft timestamp, beschrieb varchar(80), qualitaet int2, verbindlkt int2, kantart varchar(10),BTREE, zonenabk varchar(12), bez varchar(150), planbeschr varchar(150), bemerk varchar(80), darst_c varchar(5), datenverw varchar(36), zustaendig varchar(36), bundesart varchar(10), nz float4, nz_art int2, gruenfz float4, laermes int2, flmass int4, br_nutzart varchar(80), br_nmass varchar(80)
Note: NUPLA_GNGRUZO
NUPLA_GNGRUZO (writer GEODATABASE_SDE_2)
    attributes: BFSNR smallint, GEMNAME char(50), RVS_ID char(100), GENEHM date, INKRAFT date, BESCHRIEB char(80), QUALITAET smallint, VERBINDLKT smallint, KANTART char(10), ZONENABK char(12), BEZ char(150), PLANBESCHR char(150), BEMERK char(80), DARST_C char(5), DATENVERW char(36), ZUSTAENDIG char(36), BUNDESART char(10), NZ float, NZ_ART smallint, GRUENFZ float, LAERMES smallint, FLMASS integer, BR_NUTZART char(80), BR_NMASS char(80)
Note: NUPLA_UELARMES
NUPLA_UELARMES (writer GEODATABASE_SDE_2)
    attributes: BFSNR smallint, GEMNAME char(50), RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10)
BulkAttributeRenamer_8
    ATTRCHOICE = All Attributes
    CASE_CHANGE_TYPE = lower
    MODE_CHOICE = RENAME
    PATTERN_ACTION_DISP = CASECHANGE
    -> nupla_uelarmes (writer POSTGIS_1)
Note: geodb.nupla_uelarmes
nupla_uelarmes (writer POSTGIS_1)
    attributes: bfsnr int2, gemname varchar(50), rvs_id varchar(100), genehm timestamp, inkraft timestamp, beschrieb varchar(80), qualitaet int2, verbindlkt int2, kantart int2,BTREE, zonenabk varchar(12), bez varchar(150), planbeschr varchar(150), bemerk varchar(80), darst_c varchar(5), datenverw varchar(36), zustaendig varchar(36), bundesart varchar(10)
Note: NUPLA_UEWAABL
NUPLA_UEWAABL (writer GEODATABASE_SDE_2)
    attributes: BFSNR smallint, GEMNAME char(50), GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, RVS_ID char(100)
BulkAttributeRenamer_7
    ATTRCHOICE = All Attributes
    CASE_CHANGE_TYPE = lower
    MODE_CHOICE = RENAME
    PATTERN_ACTION_DISP = CASECHANGE
    -> nupla_uewaabl (writer POSTGIS_1)
Note: geodb.nupla_uewaabl
nupla_uewaabl (writer POSTGIS_1)
    attributes: bfsnr int2, gemname varchar(50), rvs_id varchar(100), genehm timestamp, inkraft timestamp, beschrieb varchar(80), qualitaet int2, verbindlkt int2, kantart int2,BTREE, linienabk varchar(12), bez varchar(150), planbeschr varchar(150), bemerk varchar(80), darst_c varchar(5), datenverw varchar(36), zustaendig varchar(36), bundesart varchar(10), nz float4, nz_art int2, gruenfz float4
Note: NH_NaturHeimatSchutz : PUNKT
Junction_6
    -> AttributeRenamer_4
Note: OEREB2.PUNKT
PUNKT (writer GEODATABASE_SDE_1)
    attributes: PUN_OID char(128), PUN_XTF_ID char(128), PUN_PUBLIZIERTAB date, PUN_METAGEO_DE char(1023), PUN_METAGEO_FR char(1023), PUN_LIEFEREINHEIT integer, EIB_OID char(128), AMT_OID char(128), RES_ID integer
Note: NUPLA_UEPT
NUPLA_UEPT (writer GEODATABASE_SDE_2)
    attributes: BFSNR smallint, GEMNAME char(50), RVS_ID char(100), GENEHM date, INKRAFT date, BESCHRIEB char(80), QUALITAET smallint, VERBINDLKT smallint, KANTART smallint, PUNKTABK char(12), BEZ char(150), PLANBESCHR char(150), BEMERK char(80), DARST_C char(5), DATENVERW char(36), ZUSTAENDIG char(36), BUNDESART char(10), ORI float, BEDEUT smallint, SCHUTZG smallint
BulkAttributeRenamer_6
    ATTRCHOICE = All Attributes
    CASE_CHANGE_TYPE = lower
    MODE_CHOICE = RENAME
    PATTERN_ACTION_DISP = CASECHANGE
    -> nupla_uept (writer POSTGIS_1)
Note: geodb.nupla_uept
nupla_uept (writer POSTGIS_1)
    attributes: bfsnr int2, gemname varchar(50), rvs_id varchar(100), genehm timestamp, inkraft timestamp, beschrieb varchar(80), qualitaet int2, verbindlkt int2, kantart int2,BTREE, punktabk varchar(12), bez varchar(150), planbeschr varchar(150), bemerk varchar(80), darst_c varchar(5), datenverw varchar(36), zustaendig varchar(36), bundesart varchar(10), ori float4, bedeut int2, schutzg int2
FeatureHolder_3
    -> NUPLA_UELN (writer GEODATABASE_SDE_2)
    -> BulkAttributeRenamer_4
Note: NUPLA_UELN
NUPLA_UELN (writer GEODATABASE_SDE_2)
    attributes: BFSNR smallint, GEMNAME char(50), RVS_ID char(100), GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, ABSTLINKS float, ABSTRECHTS float, ABSTDEF smallint, STATUS smallint
BulkAttributeRenamer_4
    ATTRCHOICE = All Attributes
    CASE_CHANGE_TYPE = lower
    MODE_CHOICE = RENAME
    PATTERN_ACTION_DISP = CASECHANGE
    -> nupla_ueln (writer POSTGIS_1)
Note: geodb.nupla_ueln
nupla_ueln (writer POSTGIS_1)
    attributes: bfsnr int2, gemname varchar(50), rvs_id varchar(100), genehm timestamp, inkraft timestamp, beschrieb varchar(80), qualitaet int2, verbindlkt int2, kantart int2,BTREE, linienabk varchar(12), bez varchar(150), planbeschr varchar(150), bemerk varchar(80), darst_c varchar(5), datenverw varchar(36), zustaendig varchar(36), bundesart varchar(10), nz float4, nz_art int2, gruenfz float4, bedeut int2, schutzg int2, gw_nat int2, gw_bed int2, abstlinks float4, abstrechts float4, abstdef int2, status int2
FeatureHolder_6
    -> LINIE (writer GEODATABASE_SDE_1)
    -> Junction_3
Note: ArcStroker : Input
Junction_3
    -> Junction_4
Junction_4
    -> ArcStroker
Note: OEREB2.LINIE
LINIE (writer GEODATABASE_SDE_1)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
Note: Verwendete Aemter weiter- / verarbeiten
FeatureHolder_2
    -> FeatureMerger_4 [SUPPLIER]
    -> FeatureMerger_3 [SUPPLIER]
FeatureMerger_4
    IGNORE_NULLS = Yes
    JOIN_KEYS = @Value(AMT_ID) @Value(ZUSTAENDIG) AUTO
    MERGE_TYPE = Attributes Only
    PROCESS_DUPS = No
    SUPPLIERS_FIRST = No
    SUPPLIER_PREFIX_DUMMY = YES
    MERGED -> AttributeRemover_7
FeatureMerger_3
    IGNORE_NULLS = Yes
    JOIN_KEYS = @Value(AMT_ID) @Value(DATENVERW) AUTO
    MERGE_TYPE = Attributes Only
    PROCESS_DUPS = No
    SUPPLIERS_FIRST = No
    SUPPLIER_PREFIX_DUMMY = YES
    MERGED -> AttributeRemover_7
AttributeRemover_7
    REMOVE_ATTRS = DATENVERW,ZUSTAENDIG
    -> NUPLA_AMTT (writer GEODATABASE_SDE_2)
    -> BulkAttributeRenamer
Note: NUPLA_AMTT
NUPLA_AMTT (writer GEODATABASE_SDE_2)
    attributes: BFSNR smallint, GEMNAME char(50), AMTNAME char(200), UID_AMT char(15), AMTIMWEB char(100), AMT_ID char(36)
BulkAttributeRenamer
    ATTRCHOICE = All Attributes
    CASE_CHANGE_TYPE = lower
    MODE_CHOICE = RENAME
    PATTERN_ACTION_DISP = CASECHANGE
    -> nupla_amtt (writer POSTGIS_1)
Note: geodb.nupla_amtt
nupla_amtt (writer POSTGIS_1)
    attributes: bfsnr int2, gemname varchar(50), amtname varchar(200), uid_amt varchar(15), amtimweb varchar(100), amt_id varchar(36)
Aggregator
    ACCUM_ATTRS_NAME = Yes
    GROUP_BY = RES_ID EIB_SORT DAR_OID EIB_OID EIB_AUSSAGE_FR schema EIB_ARTCODE STH_ID EIB_AUSSAGE_DE EIB_XTF_ID EIB_PUBLIZIERTAB
    MODE = Attributes Only
    ORDERED = No
    SEP = ,
    AGGREGATE -> EIGENTUMSBESCHRAENKUNG (writer ORACLE8I_DB_1)
    AGGREGATE -> AttributeRemover
    AGGREGATE -> AttributeValueMapper_2
    AGGREGATE -> AttributeKeeper_6
AttributeKeeper_6
    KEEP_ATTRS = DAR_OID,schema
    -> DuplicateFilter
DuplicateFilter
    INPUT_ORDERED_CHOICE = No
    KEYATTR = DAR_OID
    UNIQUE -> PythonCaller_2
PythonCaller_2
    NEW_ATTRIBUTES = DAR_VERWEISWMS_DE DAR_VERWEISWMS_FR
    PYTHONSOURCE:
      import fme
      import fmeobjects

      def processFeature(feature):
          dar_oid = feature.getAttribute("DAR_OID")
          layername = ""

          if dar_oid.endswith(".11"):
              layername = "geodb.nupla_gngruzo"
          elif dar_oid.endswith(".12"):
              layername = "geodb.nupla_uefl_1"
          elif dar_oid.endswith(".13"):
              layername = "geodb.nupla_uefl_2"
          elif dar_oid.endswith(".14"):
              layername = "geodb.nupla_ueln"
          elif dar_oid.endswith(".15"):
              layername = "geodb.nupla_uept"
          elif dar_oid.endswith(".150"):
              layername = "geodb.nupla_uelarmes"
          elif dar_oid.endswith(".170"):
              layername = "geodb.nupla_uewaabl"

          wms = FME_MacroValues['NPL_WMS_BASE'] + layername
          feature.setAttribute("DAR_VERWEISWMS_DE", wms)
          feature.setAttribute("DAR_VERWEISWMS_FR", wms)
    PYTHONSYMBOL = processFeature
    -> StringConcatenator_6
Note: DAR_LEGENDEIMWEB_DE
StringConcatenator_6
    PARM_LINE = $(OUTPUT_RV_URL)legenden/$(BFSNR)_legende_npl_de.html
    VAL_ATTR = DAR_LEGENDEIMWEB_DE
    -> StringConcatenator_7
Note: DAR_LEGENDEIMWEB_FR
StringConcatenator_7
    PARM_LINE = $(OUTPUT_RV_URL)legenden/$(BFSNR)_legende_npl_fr.html
    VAL_ATTR = DAR_LEGENDEIMWEB_FR
    -> AttributeCreator_15
Note: DAR_LIEFEREINHEIT
AttributeCreator_15
    ATTR_LIST = DAR_LIEFEREINHEIT,$(LIEFEREINHEIT)
    -> AttributeRemover_4
AttributeRemover_4
    REMOVE_ATTRS = STH_ID,LAYERNAME_BFS
    -> DARSTELLUNGSDIENST (writer ORACLE8I_DB_1)
    -> AttributeRenamer_2
DARSTELLUNGSDIENST (writer ORACLE8I_DB_1)
    attributes: DAR_OID nvarchar(128), DAR_XTF_ID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(6,0)
AttributeRenamer_2
    ATTR_TABLE:
      RENAME_SET_DEFAULT DAR_OID > id
      RENAME_SET_DEFAULT DAR_VERWEISWMS_DE > reference_wms
    -> JSONTemplater_5 [ROOT]
Note: Information-Attribut als JSON-String / aufbauen.
JSONTemplater_5
    RESULT_ATTRIBUTE = legend_at_web
    ROOT_QUERY_EXPR:
      {
          "fr": fme:get-attribute("DAR_LEGENDEIMWEB_FR"),
          "de": fme:get-attribute("DAR_LEGENDEIMWEB_DE")
      }
    VISIBLE_QUERY_VALIDATE = Yes
    -> view_service (writer POSTGRES_1)
view_service (writer POSTGRES_1)
    attributes: id varchar(80),PrimaryKey, reference_wms varchar(80), legend_at_web json, liefereinheit int4
Note: OEREB2.EIGENTUMSBESCHRAENKUNG
EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), STH_ID number(10,0), EIB_SORT number(10,0), EIB_LEGENDESYMBOL_DE nvarchar(1023), EIB_LEGENDESYMBOL_FR nvarchar(1023)
AttributeRemover
    REMOVE_ATTRS = EIB_PUBLIZIERTAB,EIB_AUSSAGE_DE,EIB_AUSSAGE_FR,EIB_ARTCODE,EIB_SORT,RES_ID,DAR_OID
    -> TestFilter
TestFilter
    DEFAULT_VALUE = UEBRIGE
    TEST_LIST = BOOL_OP,OR,COMPOSITE_TEST,<Unused>,TEST_CLAUSE,"NUM_TEST @Value(STH_ID) = 150",LAERMEMPFINDLICHKEITSSTUFEN,BOOL_OP,OR,COMPOSITE_TEST,<Unused>,TEST_CLAUSE,"NUM_TEST @Value(STH_ID) = 170",WALDBAULINIEN
    LAERMEMPFINDLICHKEITSSTUFEN -> AttributeCreator_9
    WALDBAULINIEN -> AttributeCreator_4
    WALDBAULINIEN -> AttributeCreator_3
    WALDBAULINIEN -> AttributeCreator
    UEBRIGE -> AttributeCreator_5
    UEBRIGE -> AttributeCreator_6
    UEBRIGE -> AttributeCreator_7
    UEBRIGE -> AttributeCreator_8
AttributeRemover_6
    REMOVE_ATTRS = schema
    -> AttributeRemover_19
Note: Subthema dt mappen
AttributeValueMapper_2
    DEFAULT_VALUE = FME_NULL_VALUE
    DIRECTION = Forward (Source To Destination)
    LUT = 11,Zonenflächen der Grundnutzung,12,Überlagernde Zonenflächen,13,Andere flächenbezogene Festlegungen,14,Linienbezogene Festlegungen,15,Punktbezogene Festlegungen,16,Zonenflächen Grundnutzung (Nutzungszonen),17,Zonenflächen Grundnutzung (Bauklassen)
    SRC = STH_ID
    VAL_ATTR = STH_DE
    -> AttributeValueMapper_3
Note: Subthema fr mappen
AttributeValueMapper_3
    DEFAULT_VALUE = FME_NULL_VALUE
    DIRECTION = Forward (Source To Destination)
    LUT = 11,Surfaces de zones de l’affectation primaire,12,Zones superposées,13,Autres périmètres superposés,14,Contenus linéaires,15,Contenus ponctuels,16,Surfaces de zones de l’affectation primaire (Type de zone d'affectation),17,Surfaces de zones de l’affectation primaire (Classe de construction)
    SRC = STH_ID
    VAL_ATTR = STH_FR
    -> TestFilter_2
TestFilter_2
    DEFAULT_VALUE = LAERM_WALDBAUL
    TEST_LIST = "BOOL_OP,OR,COMPOSITE_TEST,""""""<Unused>"""""",TEST_CLAUSE,TEST @Value(schema) = land_use_plans",NUTZUNGSPLANUNG
    NUTZUNGSPLANUNG -> JSONTemplater [ROOT]
    LAERM_WALDBAUL -> AttributeRenamer_7
Note: Subthema als JSON
JSONTemplater
    RESULT_ATTRIBUTE = sub_theme
    ROOT_QUERY_EXPR:
      {
          "fr": fme:get-attribute("STH_FR"),
          "de": fme:get-attribute("STH_DE")
      }
    VISIBLE_QUERY_VALIDATE = Yes
    -> AttributeRenamer_7
AttributeRenamer_7
    ATTR_TABLE:
      RENAME_SET_DEFAULT EIB_OID > id
      RENAME_SET_DEFAULT EIB_PUBLIZIERTAB > published_from
      RENAME_SET_DEFAULT DAR_OID > view_service_id
    -> JSONTemplater_2 [ROOT]
Note: Information-Attribut als JSON-String / aufbauen.
JSONTemplater_2
    RESULT_ATTRIBUTE = information
    ROOT_QUERY_EXPR:
      {
          "fr": fme:get-attribute("EIB_AUSSAGE_FR"),
          "de": fme:get-attribute("EIB_AUSSAGE_DE")
      }
    VISIBLE_QUERY_VALIDATE = Yes
    -> AttributeValueMapper
Note: Topic mappen / (Topic <> Schema)
AttributeValueMapper
    DIRECTION = Forward (Source To Destination)
    LUT = $(LAERM_SCHEMA),$(LAERM_TOPIC),$(NPL_SCHEMA),$(NPL_TOPIC),$(WALDABST_SCHEMA),$(WALDABST_TOPIC)
    SRC = schema
    VAL_ATTR = topic
    -> AttributeCreator_12
AttributeCreator_12
    ATTR_TABLE:
      SET_TO office_id = $(AMT_OID)
      SET_TO liefereinheit = $(LIEFEREINHEIT)
      SET_TO type_code = t.b.d.
      SET_TO type_code_list = t.b.d.
    -> AttributeKeeper_3
AttributeKeeper_3
    KEEP_ATTRS = information,view_service_id,id,published_from,type_code,schema,type_code_list,liefereinheit,topic,sub_theme,office_id
    -> public_law_restriction (writer POSTGRES_3)
    -> legend_entry (writer POSTGRES_4)
Note: Disabled, wird erst in s49 abgefüllt / (inkl. Aggregation).
legend_entry (writer POSTGRES_4) [off]
    attributes: id varchar(80),PrimaryKey, symbol varchar(80), symbol_url varchar(80), legend_text json, type_code varchar(40), type_code_list varchar(80), topic varchar(80), sub_theme json, other_theme varchar(80), view_service_id varchar(80), liefereinheit int4
public_law_restriction (writer POSTGRES_3)
    attributes: id varchar(80),PrimaryKey, information json, topic varchar(80), sub_theme json, other_theme varchar(80), type_code varchar(40), type_code_list varchar(80), law_status varchar(80), published_from date, view_service_id varchar(80), office_id varchar(80), liefereinheit int4
FeatureHolder_4
    -> NUPLA_UEFL (writer GEODATABASE_SDE_2)
    -> BulkAttributeRenamer_5
BulkAttributeRenamer_5
    ATTRCHOICE = All Attributes
    CASE_CHANGE_TYPE = lower
    MODE_CHOICE = RENAME
    PATTERN_ACTION_DISP = CASECHANGE
    -> nupla_uefl (writer POSTGIS_1)
Note: geodb.nupla_uefl
nupla_uefl (writer POSTGIS_1)
    attributes: bfsnr int2, gemname varchar(50), rvs_id varchar(100), genehm timestamp, inkraft timestamp, beschrieb varchar(80), qualitaet int2, verbindlkt int2, kantart int2, zonenabk varchar(12), bez varchar(150), planbeschr varchar(150), bemerk varchar(80), darst_c varchar(5), datenverw varchar(36), zustaendig varchar(36), bundesart varchar(10), nz float4, nz_art int2, gruenfz float4, bedeut int2, schutzg int2, gw_nat int2, gw_bed int2, ve_gueltig timestamp, ve_beschw int2, ve_thema int2
Note: NUPLA_UEFL
NUPLA_UEFL (writer GEODATABASE_SDE_2)
    attributes: BFSNR smallint, GEMNAME char(50), RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, VE_GUELTIG date, VE_BESCHW smallint, VE_THEMA smallint
FeatureHolder_5
    -> FLAECHE (writer GEODATABASE_SDE_1)
    -> Junction
Note: ArcStroker : Input
Junction
    -> Junction_2
Junction_2
    -> ArcStroker
ArcStroker
    MAKE_POLY = No
    NUM = $(STROKER)
    STROKE_CHOICE = Number of Interpolated Edges
    TOLERANCE_VAL = 0.0
    STROKED -> GeometryRefiner
GeometryRefiner
    -> AttributeRenamer_4
AttributeRenamer_4
    ATTR_TABLE:
      RENAME_SET_DEFAULT PUN_OID > id
      RENAME_SET_DEFAULT PUN_PUBLIZIERTAB > published_from
      RENAME_SET_DEFAULT FLA_OID > id
      RENAME_SET_DEFAULT FLA_PUBLIZIERTAB > published_from
      RENAME_SET_DEFAULT LIN_OID > id
      RENAME_SET_DEFAULT LIN_PUBLIZIERTAB > published_from
      RENAME_SET_DEFAULT EIB_OID > public_law_restriction_id
    -> AttributeKeeper_2
AttributeKeeper_2
    KEEP_ATTRS = id,published_from,schema,public_law_restriction_id
    -> AttributeCreator_10
AttributeCreator_10
    ATTR_TABLE = SET_TO office_id = $(AMT_OID)
    -> Aggregator_8
Note: Hetereogenous Aggregate: / GeometryCollection
Aggregator_8
    ACCUM_ATTRS_NAME = Use Attributes From One Feature
    AGGREGATE_TYPE = Heterogeneous Collection
    GROUP_BY = id
    MODE = Geometry - Assemble One Level
    ORDERED = No
    SEP = ,
    AGGREGATE -> AttributeFilter_2
AttributeFilter_2
    ATTR_NAME = schema
    ATTR_VALUES = <Empty>,<Missing>,<Null>,<Unfiltered>,land_use_plans,forest_distance_lines,noise_sensitivity_levels
    <EMPTY> -> Terminator
    <MISSING> -> Terminator
    <NULL> -> Terminator
    <UNFILTERED> -> Terminator
    land_use_plans -> geometry (writer POSTGIS_2)
    forest_distance_lines -> geometry (writer POSTGIS_2)
    noise_sensitivity_levels -> geometry (writer POSTGIS_2)
Terminator
    MESSAGE = Translation Terminated (Feature ohne Attribut "schema")
geometry (writer POSTGIS_2)
    attributes: id varchar(80), law_status varchar(80), published_from date, geo_metadata varchar(80), public_law_restriction_id varchar(80), office_id varchar(80), liefereinheit int4
geometry (writer POSTGIS_2)
    attributes: id varchar(80), law_status varchar(80), published_from date, geo_metadata varchar(80), public_law_restriction_id varchar(80), office_id varchar(80), liefereinheit int4
geometry (writer POSTGIS_2)
    attributes: id varchar(80), law_status varchar(80), published_from date, geo_metadata varchar(80), public_law_restriction_id varchar(80), office_id varchar(80), liefereinheit int4
Note: OEREB2.FLAECHE
FLAECHE (writer GEODATABASE_SDE_1)
    attributes: FLA_OID char(128), FLA_XTF_ID char(128), FLA_PUBLIZIERTAB date, FLA_METAGEO_DE char(1023), FLA_METAGEO_FR char(1023), FLA_LIEFEREINHEIT integer, EIB_OID char(128), AMT_OID char(128), RES_ID integer
Note: RV weiterverarbeiten
FeatureHolder
    -> FeatureMerger_2 [REQUESTOR]
Note: Dokument vorbereiten
Dokument_vorbereiten: Dokument vorbereiten
    ABKUERZUNG = @Value(Abkuerzung)
    AMT_ID = @Value(AMT_ID)
    AMT_XTF_ID = @Value(AMT_XTF_ID)
    ART_DOKU = @Value(Art_Doku)
    DOKUMENT = @Value(Dokument)
    GEMEINDE = @Value(Gemeinde)
    OFFIZIELLENR = @Value(OffizielleNr)
    OFFIZIELLERTITEL = @Value(OffiziellerTitel)
    TITEL = @Value(Titel)
    XTF_ID = @Value(xtf_id)
    ZUSTAENDIGESTELLE = @Value(ZustaendigeStelle)
    Alle_Dokumente -> HINWEIDOK-IDs_ersetzen [AlleDokumente]
    Alle_Dokumente -> FeatureMerger_2 [SUPPLIER]
    Alle_Dokumente -> FeatureMerger_12 [REQUESTOR]
Note: Alle Dokumente, die in den RV- / Tabellen direkt verlinkt sind.
FeatureMerger_2
    IGNORE_NULLS = Yes
    JOIN_KEYS = @Value(Vorschrift) @Value(VOR_XTF_ID) AUTO
    MERGE_TYPE = Attributes Only
    PROCESS_DUPS = No
    SUPPLIERS_FIRST = No
    SUPPLIER_PREFIX_DUMMY = YES
    MERGED -> AttributeRemover_8
AttributeRemover_8
    REMOVE_ATTRS = Vorschrift,EIB_XTF_ID,VOR_XTF_ID,Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset,AMT_XTF_ID,AMTNAME,UID_AMT,AMTIMWEB,ZUSTAENDIG
    -> FeatureMerger_11 [REQUESTOR]
    -> UUIDGenerator_7
Note: HiinweisWeitereDokumente: / alle IDs ersetzen durch UUIDs / (VOR_OID)
HINWEIDOK-IDs_ersetzen: HINWEIDOK-IDs ersetzen
    ARTIKELNR = @Value(ArtikelNr)
    HINWEIS = @Value(Hinweis)
    ORDNUNGSNUMMER = @Value(Ordnungsnummer)
    URSPRUNG = @Value(Ursprung)
    VOR_OID = @Value(VOR_OID)
    VOR_XTF_ID = @Value(VOR_XTF_ID)
    HINWEIDOK_ID_ersetzt -> HINWEIDOK_flachdruecken [HINWEIDOK]
Note: HINWEIDOK flachdruecken / (mit Views aus Verschnitt- / funktion)
HINWEIDOK_flachdruecken: HINWEIDOK flachdruecken
    HINWEIDOK_flach -> FeatureMerger_11 [SUPPLIER]
FeatureMerger_11
    GEOM_TYPE = Build Polygons
    IGNORE_NULLS = Yes
    JOIN_KEYS = @Value(VOR_OID) @Value(VOR_OIDURSPRUNG) AUTO
    LIST_NAME = duplicates
    MERGE_TYPE = Attributes Only
    PROCESS_DUPS = Yes
    SUPPLIERS_FIRST = No
    SUPPLIER_PREFIX_DUMMY = YES
    MERGED -> AttributeRemover_15
AttributeRemover_15
    REMOVE_ATTRS = HIV_ARTNR,VOR_OID,VOR_OIDURSPRUNG,VOR_OIDHINWEIS
    -> ListExploder
ListExploder
    INDEX_ATTR = _element_index
    LIST_ATTR = duplicates{}
    MODE = List Elements and Original Attributes
    LIST_FOUND -> AttributeRemover_16
AttributeRemover_16
    REMOVE_ATTRS = VOR_OIDURSPRUNG,_element_index
    -> AttributeRenamer_12
AttributeRenamer_12
    ATTR_LIST = VOR_OIDHINWEIS,VOR_OID,""
    -> Aggregator_3
Note: Es kann Duplikate geben / (v.a. in Thun)
Aggregator_3
    ACCUM_ATTRS_NAME = Yes
    GROUP_BY = VOR_OID EIB_OID schema
    MODE = Attributes Only
    ORDERED = No
    SEP = ,
    AGGREGATE -> UUIDGenerator_7
UUIDGenerator_7
    UUID_ATTR = HIV_ID
    -> AttributeRemover_18
    -> AttributeRemover_19
    -> DuplicateRemover_3
Note: Alle Duplikate entfernen
DuplicateRemover_3
    KEYATTR = VOR_OID EIB_OID
    UNIQUE -> FeatureHolder_7
FeatureHolder_7
    -> HINVOR (writer ORACLE8I_DB_1)
    -> AttributeRenamer_10
Note: OEREB2.HINVOR
HINVOR (writer ORACLE8I_DB_1)
    attributes: HIV_ID nvarchar(128), HIV_XTF_ID nvarchar(128), HIV_ARTNR nvarchar(255), HIV_LIEFEREINHEIT number(6,0), EIB_OID nvarchar(128), VOR_OID nvarchar(128)
AttributeRenamer_10
    ATTR_TABLE:
      RENAME_SET_DEFAULT HIV_ID > id
      RENAME_SET_DEFAULT EIB_OID > public_law_restriction_id
      RENAME_SET_DEFAULT VOR_OID > document_id
    -> AttributeKeeper_4
AttributeKeeper_4
    KEEP_ATTRS = document_id,schema,public_law_restriction_id,id
    -> BulkAttributeRenamer_17
    -> public_law_restriction_document (writer POSTGRES_8)
BulkAttributeRenamer_17
    ATTRCHOICE = All Attributes
    MODE_CHOICE = RENAME
    PATTERN_ACTION_DISP = ADDPREFIX
    REPLACE_STR = plrdoc_
    -> AttributeKeeper_9
AttributeKeeper_9
    KEEP_ATTRS = plrdoc_document_id,plrdoc_schema
    -> FeatureMerger99 [REQUESTOR]
public_law_restriction_document (writer POSTGRES_8)
    attributes: id varchar(80),PrimaryKey, public_law_restriction_id varchar(80), document_id varchar(80), article_numbers varchar(80), liefereinheit int4
AttributeRemover_19
    REMOVE_ATTRS = HIV_ID
    -> FeatureMerger_13 [REQUESTOR]
AttributeRemover_18
    REMOVE_ATTRS = HIV_ARTNR,EIB_OID,HIV_ID
    -> Aggregator_2
Aggregator_2
    ACCUM_ATTRS_NAME = Yes
    GROUP_BY = VOR_OID
    MODE = Attributes Only
    ORDERED = No
    SEP = ,
    AGGREGATE -> FeatureMerger_12 [SUPPLIER]
FeatureMerger_12
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> FeatureMerger_13 [SUPPLIER]
Note: Merged = REVO und HINW / NotMerged = GEGR
FeatureMerger_13
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> AttributeRenamer_13
    MERGED -> AttributeRemover_2
    NOT_MERGED -> Joiner
AttributeRemover_2
    REMOVE_ATTRS = EIB_OID,HIV_ARTNR,Art_Doku,Gemeinde,Dokument,ZustaendigeStelle,AMT_XTF_ID,AMTNAME,UID_AMT,AMTIMWEB,ZUSTAENDIG
    -> DuplicateRemover
    -> AttributeRenamer_9
AttributeRenamer_9
    ATTR_TABLE:
      RENAME_SET_DEFAULT VOR_OID > id
      RENAME_SET_DEFAULT VOR_PUBLIZIERTAB > published_from
      RENAME_SET_DEFAULT AMT_OID > office_id
    -> JSONTemplater_6 [ROOT]
Note: text_at_web-Attribut als JSON-String / aufbauen.
JSONTemplater_6
    RESULT_ATTRIBUTE = text_at_web
    ROOT_QUERY_EXPR:
      {
          "fr": fme:get-attribute("VOR_TEXTIMWEB_FR"),
          "de": fme:get-attribute("VOR_TEXTIMWEB_DE")
      }
    VISIBLE_QUERY_VALIDATE = Yes
    -> AttributeValueMapper_5
Note: document_type-Attribut / mappen
AttributeValueMapper_5
    DIRECTION = Forward (Source To Destination)
    LUT = 1,LegalProvision,2,Law,3,Hint
    SRC = VOA_ID
    VAL_ATTR = document_type
    -> AttributeCreator_13
Note: type-Attribut ist wohl immer "document"
AttributeCreator_13
    ATTR_TABLE = SET_TO type = document
    -> JSONTemplater_3 [ROOT]
Note: Title-Attribut als JSON-String / aufbauen.
JSONTemplater_3
    RESULT_ATTRIBUTE = title
    ROOT_QUERY_EXPR:
      {
          "fr": fme:get-attribute("VOR_TITEL_FR"),
          "de": fme:get-attribute("VOR_TITEL_DE")
      }
    VISIBLE_QUERY_VALIDATE = Yes
    -> AttributeCreator_14
AttributeCreator_14
    ATTR_TABLE:
      SET_TO official_title = @Value(title)
      SET_TO office_id = $(AMT_OID)
    -> AttributeKeeper_5
AttributeKeeper_5
    KEEP_ATTRS = text_at_web,document_type,type,office_id,published_from,schema,title,id,official_title
    -> BulkAttributeRenamer_18
BulkAttributeRenamer_18
    ATTRCHOICE = All Attributes
    MODE_CHOICE = RENAME
    PATTERN_ACTION_DISP = ADDPREFIX
    REPLACE_STR = doc_
    -> FeatureMerger99 [SUPPLIER]
FeatureMerger99
    ATTR_ACCUM_MODE = Merge Supplier
    ATTR_CONFLICT_RES = Use Requestor
    IGNORE_NULLS = No
    JOIN_KEYS = @Value(plrdoc_document_id) @Value(doc_id) AUTO
    MERGE_TYPE = Attributes Only
    PROCESS_DUPS = NO
    REJECT_NULL_MISSING_KEYS = No
    SUPPLIERS_FIRST = No
    MERGED -> AttributeRenamer_6
AttributeRenamer_6
    ATTR_TABLE = RENAME_SET_DEFAULT plrdoc_schema > doc_schema
    -> AttributeRemover_5
AttributeRemover_5
    REMOVE_ATTRS = plrdoc_document_id
    -> DuplicateFilter_2
DuplicateFilter_2
    INPUT_ORDERED_CHOICE = No
    KEYATTR = doc_official_title doc_document_type doc_type doc_schema doc_published_from doc_title doc_office_id doc_text_at_web doc_id
    UNIQUE -> BulkAttributeRenamer_13
BulkAttributeRenamer_13
    ATTRCHOICE = All Attributes
    CASE_DISP = YES
    MODE_CHOICE = RENAME
    PATTERN_ACTION_DISP = REMOVEPREFIX
    REPLACE_STR = doc_
    -> document_base (writer POSTGRES_5)
    -> document (writer POSTGRES_6)
document_base (writer POSTGRES_5)
    attributes: id varchar(80),PrimaryKey, text_at_web json, law_status varchar(80), published_from date, type varchar(80), liefereinheit int4
document (writer POSTGRES_6)
    attributes: document_type varchar(80), title json, official_title json, abbreviation json, official_number varchar(80), canton varchar(2), municipality int4, file varchar(80), id varchar(80),PrimaryKey, office_id varchar(80), liefereinheit int4
Note: Alle Duplikate entfernen
DuplicateRemover
    KEYATTR = VOR_OID VOR_XTF_ID VOR_TITEL_DE VOR_OFFIZIELLERTITEL_DE VOR_ABKUERZUNG_DE VOR_OFFIZIELLENR VOR_PUBLIZIERTAB VOA_ID VOR_TITEL_FR VOR_OFFIZIELLERTITEL_FR VOR_ABKUERZUNG_FR VOR_TEXTIMWEB_DE VOR_TEXTIMWEB_FR filecopy_source_dataset filecopy_dest_dataset
    UNIQUE -> VORSCHRIFT (writer ORACLE8I_DB_1)
    UNIQUE -> AttributeFilter
Note: Wenn Normalbaureglement, kein Dokument kopieren
AttributeFilter
    ATTR_NAME = filecopy_dest_dataset
    ATTR_VALUES = <EMPTY>,Normalbaureglement,<MISSING>,<NULL>,<UNFILTERED>
    <UNFILTERED> -> filecopy (writer FILECOPY_1)
filecopy (writer FILECOPY_1)
Note: OEREB2.VORSCHRIFT
VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)
Note: GEGR aus der DB holen. Die / werden separat importiert.
Joiner
    ADDED_FIELDS = VOR_TEXTIMWEB_DE VOR_TITEL_DE VOR_OFFIZIELLERTITEL_DE VOR_ABKUERZUNG_DE VOR_OFFIZIELLENR VOA_ID
    CACHE_SIZE = 5000
    DATASET = $(OEREB2_DATABASE)
    FORMAT = ORACLE8I_DB
    JOIN_KEYS = VOR_OID VOR_OID
    MATCH_RULE_DISPLAY = Must Match Exactly One (1:1)
    ORACLE8I_DB_PASSWORD = $(OEREB2_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(OEREB2_USERNAME)
    PREFETCH_EXHAUSTIVE = Yes
    TABLE = OEREB2.VORSCHRIFT
    JOINED -> AttributeRenamer_13
AttributeRenamer_13
    ATTR_LIST = EIB_OID,RVS_ID,"",VOR_TITEL_DE,TITEL,"",VOR_OFFIZIELLERTITEL_DE,OFFIZTITEL,"",VOR_ABKUERZUNG_DE,ABKUERZUNG,"",VOR_OFFIZIELLENR,OFFIZNR,"",VOR_TEXTIMWEB_DE,DOKUMENT,"",HIV_ARTNR,ARTIKELNR,""
    -> AttributeValueMapper_7
Note: ART aus VOA_ID mappen
AttributeValueMapper_7
    DIRECTION = Forward (Source To Destination)
    LUT = 1,Rechtsvorschrift,2,Gesetzliche Grundlage,3,Hinweis
    SRC = VOA_ID
    VAL_ATTR = ART
    -> Sorter
Sorter
    SORT_PARM = RVS_ID ALPHA ASCENDING ART ALPHA DESCENDING
    SORTED -> AttributeRemover_3
AttributeRemover_3
    REMOVE_ATTRS = VOR_OID,VOR_XTF_ID,Art_Doku,Gemeinde,Dokument,ZustaendigeStelle,VOR_PUBLIZIERTAB,VOA_ID,VOR_TITEL_FR,VOR_OFFIZIELLERTITEL_FR,VOR_ABKUERZUNG_FR,VOR_TEXTIMWEB_FR,filecopy_source_dataset,filecopy_dest_dataset,AMT_XTF_ID,AMTNAME,UID_AMT,AMTIMWEB,_matched_records
    -> DuplicateRemover_2
Note: Alle Duplikate entfernen
DuplicateRemover_2
    KEYATTR = RVS_ID ARTIKELNR TITEL OFFIZTITEL ABKUERZUNG OFFIZNR DOKUMENT ZUSTAENDIG ART
    UNIQUE -> NUPLA_RVST (writer GEODATABASE_SDE_2)
    UNIQUE -> BulkAttributeRenamer_9
BulkAttributeRenamer_9
    ATTRCHOICE = All Attributes
    CASE_CHANGE_TYPE = lower
    MODE_CHOICE = RENAME
    PATTERN_ACTION_DISP = CASECHANGE
    -> nupla_rvst (writer POSTGIS_1)
Note: geodb.nupla_rvst
nupla_rvst (writer POSTGIS_1)
    attributes: bfsnr int2, gemname varchar(50), rvs_id varchar(100), art varchar(40), titel varchar(200), offiztitel varchar(200), abkuerzung varchar(20), offiznr varchar(20), dokument varchar(1023), artikelnr varchar(40), ordnnr int2, zustaendig varchar(36)
Note: NUPLA_RVST
NUPLA_RVST (writer GEODATABASE_SDE_2)
    attributes: BFSNR smallint, GEMNAME char(50), RVS_ID char(100), ART char(40), TITEL char(200), OFFIZTITEL char(200), ABKUERZUNG char(20), OFFIZNR char(20), DOKUMENT char(100), ARTIKELNR char(40), ORDNNR smallint, ZUSTAENDIG char(100)
document_reference (writer POSTGRES_7) [off]
    attributes: id varchar(80),PrimaryKey, document_id varchar(80), reference_document_id varchar(80), article_numbers varchar(80), liefereinheit int4

Bookmark: GN_Grundzone
Note: GN_Grundzone
DM16NplBE.Nutzungsplanung.GN_Grundzone (reader ch.ehi.fme.Main_1)
    attributes: xtf_id xtf_char(200), ZonentypRef xtf_char(200), Genehmigung xtf_date, Inkraftsetzung xtf_date, Laermempfindlichkeit xtf_char(255), Beschrieb xtf_char(80), Planbeschriftung xtf_char(150), Qualitaet xtf_char(255), Bemerkung xtf_char(80), Flaechenmass xtf_int32
    -> GN_Grundnutzung [GN_Grundzone]
Note: GN_Grundzone_ZPP_UeO
DM16NplBE.Nutzungsplanung.GN_Grundzone_ZPP_UeO (reader ch.ehi.fme.Main_1)
    attributes: xtf_id xtf_char(200), ZonentypRef xtf_char(200), Genehmigung xtf_date, Inkraftsetzung xtf_date, Laermempfindlichkeit xtf_char(255), Beschrieb xtf_char(80), Planbeschriftung xtf_char(150), Qualitaet xtf_char(255), Bemerkung xtf_char(80), Flaechenmass xtf_int32
    -> GN_Grundnutzung [GN_Grundzone_ZPP_UeO]
Note: GN_Zonentyp
DM16NplBE.Nutzungsplanung.GN_Zonentyp (reader ch.ehi.fme.Main_1)
    attributes: xtf_id xtf_char(200), Verbindlichkeit xtf_char(255), KantArt xtf_char(255), Abkuerzung xtf_char(12), Bezeichnung xtf_char(150), BR_Nutzungsart xtf_char(80), BR_Nutzungsmass xtf_char(80), Nutzungsziffer xtf_decimal(4,2), Nutzungsziffer_Art xtf_char(255), Gruenflaechenziffer xtf_decimal(4,2), Bemerkung xtf_char(80), DarstellungCode xtf_char(5), Datenverwaltungsstelle xtf_char(200), ZustaendigeStelle xtf_char(200)
    -> GN_Grundnutzung [GN_Zonentyp]
Note: GN_ZonentypRV
DM16NplBE.Nutzungsplanung.GN_ZonentypRV (reader ch.ehi.fme.Main_1)
    attributes: xtf_id xtf_char(200), Typ xtf_char(200), Vorschrift xtf_char(200), ArtikelNr xtf_char(40)
    -> GN_Grundnutzung [GN_ZonentypRV]
GN_Grundnutzung
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BEZEICHNUNG = @Value(Bezeichnung)
    BFSNR = $(BFSNR)
    BR_NUTZUNGSART = @Value(BR_Nutzungsart)
    BR_NUTZUNGSMASS = @Value(BR_Nutzungsmass)
    DARSTELLUNGCODE = @Value(DarstellungCode)
    DATENVERWALTUNGSSTELLE = @Value(Datenverwaltungsstelle)
    FLAECHENMASS = @Value(Flaechenmass)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    INKRAFTSETZUNG = @Value(Inkraftsetzung)
    KANTART = @Value(KantArt)
    LAERMEMPFINDLICHKEIT = @Value(Laermempfindlichkeit)
    LAERM_SCHEMA = $(LAERM_SCHEMA)
    NPL_SCHEMA = $(NPL_SCHEMA)
    NUTZUNGSZIFFER = @Value(Nutzungsziffer)
    NUTZUNGSZIFFER_ART = @Value(Nutzungsziffer_Art)
    PLANBESCHRIFTUNG = @Value(Planbeschriftung)
    QUALITAET = @Value(Qualitaet)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZONENTYPREF = @Value(ZonentypRef)
    ZUSTAENDIGESTELLE = @Value(ZustaendigeStelle)
    GNZPPUEO -> NUPLA_GNZPPUEO (writer GEODATABASE_SDE_2)
    GNZPPUEO -> BulkAttributeRenamer_3
    GNGRUZO -> NUPLA_GNGRUZO (writer GEODATABASE_SDE_2)
    GNGRUZO -> BulkAttributeRenamer_2
    EIGENTUMSBESCHRAENKUNG -> Aggregator
    FLAECHE -> FeatureHolder_5
    HINVOR -> FeatureHolder
    Verwendete_Aemter -> FeatureHolder_2

Bookmark: UE_Ueberlagerung
Note: UE_FlaechenelementUeberl
DM16NplBE.Nutzungsplanung.UE_FlaechenelementUeberl (reader ch.ehi.fme.Main_1)
    attributes: xtf_id xtf_char(200), Genehmigung xtf_date, Inkraftsetzung xtf_date, Objekt xtf_char(200), Beschrieb xtf_char(80), Qualitaet xtf_char(255)
    -> UE_Ueberlagerung [UE_FlaechenelementUeberl]
Note: UE_UeberlagerungZone
DM16NplBE.Nutzungsplanung.UE_UeberlagerungZone (reader ch.ehi.fme.Main_1)
    attributes: xtf_id xtf_char(200), Verbindlichkeit xtf_char(255), KantArt xtf_char(255), Abkuerzung xtf_char(12), Bezeichnung xtf_char(150), Planbeschriftung xtf_char(150), Nutzungsziffer xtf_decimal(4,2), Nutzungsziffer_Art xtf_char(255), Gruenflaechenziffer xtf_decimal(4,2), Bemerkung xtf_char(80), DarstellungCode xtf_char(5), Datenverwaltungsstelle xtf_char(200), ZustaendigeStelle xtf_char(200)
    -> UE_Ueberlagerung [UE_UeberlagerungZone]
Note: UE_UeberlagerungZoneRV
DM16NplBE.Nutzungsplanung.UE_UeberlagerungZoneRV (reader ch.ehi.fme.Main_1)
    attributes: xtf_id xtf_char(200), Typ xtf_char(200), Vorschrift xtf_char(200), ArtikelNr xtf_char(40)
    -> UE_Ueberlagerung [UE_UeberlagerungZoneRV]
UE_Ueberlagerung
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    INKRAFTSETZUNG = @Value(Inkraftsetzung)
    KANTART = @Value(KantArt)
    LAERM_SCHEMA = $(LAERM_SCHEMA)
    NPL_SCHEMA = $(NPL_SCHEMA)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    UELARMES -> NUPLA_UELARMES (writer GEODATABASE_SDE_2)
    UELARMES -> BulkAttributeRenamer_8
    EIGENTUMSBESCHRAENKUNG -> Aggregator
    FLAECHE -> FeatureHolder_5
    UEFL -> FeatureHolder_4
    Verwendete_Aemter -> FeatureHolder_2
    HINVOR -> FeatureHolder

Bookmark: UE_Abstandslinie
Note: UE_AbstandslinieRV
DM16NplBE.Nutzungsplanung.UE_AbstandslinieRV (reader ch.ehi.fme.Main_1)
    attributes: xtf_id xtf_char(200), Typ xtf_char(200), Vorschrift xtf_char(200), ArtikelNr xtf_char(40)
    -> UE_Abstandslinie [UE_AbstandslinieRV]
Note: UE_LinienelementAbstand
DM16NplBE.Nutzungsplanung.UE_LinienelementAbstand (reader ch.ehi.fme.Main_1)
    attributes: xtf_id xtf_char(200), Objekt xtf_char(200), Beschrieb xtf_char(80), Genehmigung xtf_date, Inkraftsetzung xtf_date, Qualitaet xtf_char(255)
    -> UE_Abstandslinie [UE_LinienelementAbstand]
Note: UE_Abstandslinie
DM16NplBE.Nutzungsplanung.UE_Abstandslinie (reader ch.ehi.fme.Main_1)
    attributes: xtf_id xtf_char(200), Verbindlichkeit xtf_char(255), KantArt xtf_char(255), Abkuerzung xtf_char(12), Bezeichnung xtf_char(150), Planbeschriftung xtf_char(150), Nutzungsziffer xtf_decimal(4,2), Nutzungsziffer_Art xtf_char(255), Gruenflaechenziffer xtf_decimal(4,2), Bemerkung xtf_char(80), DarstellungCode xtf_char(5), Datenverwaltungsstelle xtf_char(200), ZustaendigeStelle xtf_char(200)
    -> UE_Abstandslinie [UE_Abstandslinie]
UE_Abstandslinie
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    INKRAFTSETZUNG = @Value(Inkraftsetzung)
    KANTART = @Value(KantArt)
    LAERM_SCHEMA = $(LAERM_SCHEMA)
    NPL_SCHEMA = $(NPL_SCHEMA)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    EIGENTUMSBESCHRAENKUNG -> Aggregator
    UELN -> FeatureHolder_3
    LINIE -> FeatureHolder_6
    UEWAABL -> NUPLA_UEWAABL (writer GEODATABASE_SDE_2)
    UEWAABL -> BulkAttributeRenamer_7
    HINVOR -> FeatureHolder
    Verwendete_Aemter -> FeatureHolder_2

Bookmark: NH_NHSchutz
Note: NH_PunktelementNHS
DM16NplBE.Nutzungsplanung.NH_PunktelementNHS (reader ch.ehi.fme.Main_1)
    attributes: xtf_id xtf_char(200), Objekt xtf_char(200), Beschrieb xtf_char(80), Genehmigung xtf_date, Inkraftsetzung xtf_date, Qualitaet xtf_char(255), Ori xtf_decimal(5,1)
    -> NH_NaturHeimatSchutz [NH_PunktelementNHS]
Note: NH_FlaechenelementNHS
DM16NplBE.Nutzungsplanung.NH_FlaechenelementNHS (reader ch.ehi.fme.Main_1)
    attributes: xtf_id xtf_char(200), Objekt xtf_char(200), Beschrieb xtf_char(80), Genehmigung xtf_date, Inkraftsetzung xtf_date, Qualitaet xtf_char(255)
    -> NH_NaturHeimatSchutz [NH_FlaechenelementNHS]
Note: NH_LinienelementNHS
DM16NplBE.Nutzungsplanung.NH_LinienelementNHS (reader ch.ehi.fme.Main_1)
    attributes: xtf_id xtf_char(200), Objekt xtf_char(200), Beschrieb xtf_char(80), Genehmigung xtf_date, Inkraftsetzung xtf_date, Qualitaet xtf_char(255)
    -> NH_NaturHeimatSchutz [NH_LinienelementNHS]
Note: NH_NHSchutz
DM16NplBE.Nutzungsplanung.NH_NHSchutz (reader ch.ehi.fme.Main_1)
    attributes: xtf_id xtf_char(200), Verbindlichkeit xtf_char(255), KantArt xtf_char(255), Abkuerzung xtf_char(12), Bezeichnung xtf_char(150), Bedeutung xtf_char(255), Schutzgrad xtf_char(255), Planbeschriftung xtf_char(150), Bemerkung xtf_char(80), DarstellungCode xtf_char(5), Datenverwaltungsstelle xtf_char(200), ZustaendigeStelle xtf_char(200)
    -> NH_NaturHeimatSchutz [NH_NHSchutz]
Note: NH_NHSchutzRV
DM16NplBE.Nutzungsplanung.NH_NHSchutzRV (reader ch.ehi.fme.Main_1)
    attributes: xtf_id xtf_char(200), Typ xtf_char(200), Vorschrift xtf_char(200), ArtikelNr xtf_char(40)
    -> NH_NaturHeimatSchutz [NH_NHSchutzRV]
NH_NaturHeimatSchutz
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEDEUTUNG = @Value(Bedeutung)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    KANTART = @Value(KantArt)
    LAERM_SCHEMA = $(LAERM_SCHEMA)
    NPL_SCHEMA = $(NPL_SCHEMA)
    OBJEKT = @Value(Objekt)
    ORI = @Value(Ori)
    PLANBESCHRIFTUNG = @Value(Planbeschriftung)
    QUALITAET = @Value(Qualitaet)
    SCHUTZGRAD = @Value(Schutzgrad)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    UEFL -> FeatureHolder_4
    FLAECHE -> FeatureHolder_5
    EIGENTUMSBESCHRAENKUNG -> Aggregator
    UELN -> FeatureHolder_3
    LINIE -> FeatureHolder_6
    UEPT -> NUPLA_UEPT (writer GEODATABASE_SDE_2)
    UEPT -> BulkAttributeRenamer_6
    PUNKT -> PUNKT (writer GEODATABASE_SDE_1)
    PUNKT -> Junction_5
    HINVOR -> FeatureHolder
    Verwendete_Aemter -> FeatureHolder_2
Note: AttributeRenamer_4 : Input
Junction_5
    -> Junction_6

Bookmark: WE_WegRoute
Note: WE_FlaechenelementWeg
DM16NplBE.Nutzungsplanung.WE_FlaechenelementWeg (reader ch.ehi.fme.Main_1)
    attributes: xtf_id xtf_char(200), Objekt xtf_char(200), Genehmigung xtf_date, Inkraftsetzung xtf_date, Qualitaet xtf_char(255)
    -> WE_WegRoute [WE_FlaechenelementWeg]
Note: WE_LinienelementWeg
DM16NplBE.Nutzungsplanung.WE_LinienelementWeg (reader ch.ehi.fme.Main_1)
    attributes: xtf_id xtf_char(200), Objekt xtf_char(200), Genehmigung xtf_date, Inkraftsetzung xtf_date, Qualitaet xtf_char(255)
    -> WE_WegRoute [WE_LinienelementWeg]
Note: WE_WegRoute
DM16NplBE.Nutzungsplanung.WE_WegRoute (reader ch.ehi.fme.Main_1)
    attributes: xtf_id xtf_char(200), Verbindlichkeit xtf_char(255), Art xtf_char(255), Bezeichnung xtf_char(150), Bedeutung xtf_char(255), Schutzgrad xtf_char(255), DarstellungCode xtf_char(5), Planbeschriftung xtf_char(150), Datenverwaltungsstelle xtf_char(200), ZustaendigeStelle xtf_char(200)
    -> WE_WegRoute [WE_WegRoute]
Note: WE_WegRouteRV
DM16NplBE.Nutzungsplanung.WE_WegRouteRV (reader ch.ehi.fme.Main_1)
    attributes: xtf_id xtf_char(200), Typ xtf_char(200), Vorschrift xtf_char(200), ArtikelNr xtf_char(40)
    -> WE_WegRoute [WE_WegRouteRV]
WE_WegRoute
    AMTIMWEB = @Value(AMTIMWEB)
    AMTNAME = @Value(AMTNAME)
    AMT_ID = @Value(AMT_ID)
    AMT_XTF_ID = @Value(AMT_XTF_ID)
    ART = @Value(Art)
    ARTIKELNR = @Value(ArtikelNr)
    BEDEUTUNG = @Value(Bedeutung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    LAERM_SCHEMA = $(LAERM_SCHEMA)
    NPL_SCHEMA = $(NPL_SCHEMA)
    OBJEKT = @Value(Objekt)
    PLANBESCHRIFTUNG = @Value(Planbeschriftung)
    QUALITAET = @Value(Qualitaet)
    SCHUTZGRAD = @Value(Schutzgrad)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    UEFL -> FeatureHolder_4
    FLAECHE -> FeatureHolder_5
    EIGENTUMSBESCHRAENKUNG -> Aggregator
    LINIE -> FeatureHolder_6
    UELN -> FeatureHolder_3
    HINVOR -> FeatureHolder
    Verwendete_Aemter -> FeatureHolder_2

Bookmark: GW_Gewaesser
Note: GW_LinienelementGew
DM16NplBE.Nutzungsplanung.GW_LinienelementGew (reader ch.ehi.fme.Main_1)
    attributes: xtf_id xtf_char(200), Objekt xtf_char(200), Genehmigung xtf_date, Inkraftsetzung xtf_date, Qualitaet xtf_char(255)
    -> GW_Gewaesser [GW_LinienelementGew]
Note: GW_Gewaesser
DM16NplBE.Nutzungsplanung.GW_Gewaesser (reader ch.ehi.fme.Main_1)
    attributes: xtf_id xtf_char(200), Verbindlichkeit xtf_char(255), Art xtf_char(255), Oekomorph_Natuerlichkeit xtf_char(255), Kulturhist_Bedeutung xtf_char(255), Bezeichnung xtf_char(150), Planbeschriftung xtf_char(150), Bemerkung xtf_char(80), Datenverwaltungsstelle xtf_char(200), ZustaendigeStelle xtf_char(200), DarstellungCode xtf_char(5)
    -> GW_Gewaesser [GW_Gewaesser]
Note: GW_FlaechenelementGew
DM16NplBE.Nutzungsplanung.GW_FlaechenelementGew (reader ch.ehi.fme.Main_1)
    attributes: xtf_id xtf_char(200), Objekt xtf_char(200), Genehmigung xtf_date, Inkraftsetzung xtf_date, Qualitaet xtf_char(255)
    -> GW_Gewaesser [GW_FlaechenelementGew]
Note: GW_GewaesserRV
DM16NplBE.Nutzungsplanung.GW_GewaesserRV (reader ch.ehi.fme.Main_1)
    attributes: xtf_id xtf_char(200), Typ xtf_char(200), Vorschrift xtf_char(200), ArtikelNr xtf_char(40)
    -> GW_Gewaesser [GW_GewaesserRV]
GW_Gewaesser
    AMTIMWEB = @Value(AMTIMWEB)
    AMTNAME = @Value(AMTNAME)
    AMT_ID = @Value(AMT_ID)
    AMT_XTF_ID = @Value(AMT_XTF_ID)
    ART = @Value(Art)
    ARTIKELNR = @Value(ArtikelNr)
    BEMERKUNG = @Value(Bemerkung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    KULTURHIST_BEDEUTUNG = @Value(Kulturhist_Bedeutung)
    LAERM_SCHEMA = $(LAERM_SCHEMA)
    NPL_SCHEMA = $(NPL_SCHEMA)
    OBJEKT = @Value(Objekt)
    OEKOMORPH_NATUERLICHKEIT = @Value(Oekomorph_Natuerlichkeit)
    PLANBESCHRIFTUNG = @Value(Planbeschriftung)
    QUALITAET = @Value(Qualitaet)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    UEFL -> FeatureHolder_4
    FLAECHE -> FeatureHolder_5
    EIGENTUMSBESCHRAENKUNG -> Aggregator
    LINIE -> FeatureHolder_6
    UELN -> FeatureHolder_3
    HINVOR -> FeatureHolder
    Verwendete_Aemter -> FeatureHolder_2

Bookmark: GR_Gewaesserraum
Note: GR_Gewaesserraumflaeche
DM16NplBE.Nutzungsplanung.GR_Gewaesserraumflaeche (reader ch.ehi.fme.Main_1)
    attributes: xtf_id xtf_char(200), Objekt xtf_char(200), Qualitaet xtf_char(255), Genehmigung xtf_date, Inkraftsetzung xtf_date
    -> GR_Gewaesserraum [GR_Gewaesserraumflaeche]
Note: GR_Gewaesserraumlinie
DM16NplBE.Nutzungsplanung.GR_Gewaesserraumlinie (reader ch.ehi.fme.Main_1)
    attributes: xtf_id xtf_char(200), Objekt xtf_char(200), AbstandLinks xtf_decimal(5,2), AbstandRechts xtf_decimal(5,2), AbstandDefinition xtf_char(255), Qualitaet xtf_char(255), Genehmigung xtf_date, Inkraftsetzung xtf_date
    -> GR_Gewaesserraum [GR_Gewaesserraumlinie]
Note: GR_Gewaesserraum
DM16NplBE.Nutzungsplanung.GR_Gewaesserraum (reader ch.ehi.fme.Main_1)
    attributes: xtf_id xtf_char(200), Verbindlichkeit xtf_char(255), Bemerkung xtf_char(80), Bezeichnung xtf_char(150), DarstellungCode xtf_char(5), Datenverwaltungsstelle xtf_char(200), ZustaendigeStelle xtf_char(200)
    -> GR_Gewaesserraum [GR_Gewaesserraum]
Note: GR_GewaesserraumRV
DM16NplBE.Nutzungsplanung.GR_GewaesserraumRV (reader ch.ehi.fme.Main_1)
    attributes: xtf_id xtf_char(200), Typ xtf_char(200), Vorschrift xtf_char(200), ArtikelNr xtf_char(40)
    -> GR_Gewaesserraum [GR_GewaesserraumRV]
GR_Gewaesserraum
    ABSTANDDEFINITION = @Value(AbstandDefinition)
    ABSTANDLINKS = @Value(AbstandLinks)
    ABSTANDRECHTS = @Value(AbstandRechts)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    LAERM_SCHEMA = $(LAERM_SCHEMA)
    NPL_SCHEMA = $(NPL_SCHEMA)
    OBJEKT = @Value(Objekt)
    QUALITAET = @Value(Qualitaet)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    UEFL -> FeatureHolder_4
    FLAECHE -> FeatureHolder_5
    EIGENTUMSBESCHRAENKUNG -> Aggregator
    LINIE -> FeatureHolder_6
    UELN -> FeatureHolder_3
    HINVOR -> FeatureHolder
    Verwendete_Aemter -> FeatureHolder_2

Bookmark: Vorübergehende Einschränkung (ohne Hinweise!)
Note: VE_Vor_Einschraenkung
DM16NplBE.Nutzungsplanung.VE_Vor_Einschraenkung (reader ch.ehi.fme.Main_1)
    attributes: xtf_id xtf_char(200), Verbindlichkeit xtf_char(255), KantArt xtf_char(255), Gueltig_bis xtf_date, Beschwerde_haengig xtf_char(255), Abkuerzung xtf_char(12), Planbeschriftung xtf_char(150), Bezeichnung xtf_char(150), Nutzungsziffer xtf_decimal(4,2), Nutzungsziffer_Art xtf_char(255), Gruenflaechenziffer xtf_decimal(4,2), Bemerkung xtf_char(80), ThemaLaufendeAenderung xtf_char(255), DarstellungCode xtf_char(5), Datenverwaltungsstelle xtf_char(200), ZustaendigeStelle xtf_char(200)
    -> VE_Vor_Einschraenkung [VE_Vor_Einschraenkung]
Note: VE_FlaechenelementEinschr
DM16NplBE.Nutzungsplanung.VE_FlaechenelementEinschr (reader ch.ehi.fme.Main_1)
    attributes: xtf_id xtf_char(200), Objekt xtf_char(200), Genehmigung xtf_date, Inkraftsetzung xtf_date, Beschrieb xtf_char(80), Qualitaet xtf_char(255)
    -> VE_Vor_Einschraenkung [VE_FlaechenelementEinschr]
Note: VE_Vor_EinschraenkungRV
DM16NplBE.Nutzungsplanung.VE_Vor_EinschraenkungRV (reader ch.ehi.fme.Main_1)
    attributes: xtf_id xtf_char(200), Typ xtf_char(200), Vorschrift xtf_char(200), ArtikelNr xtf_char(40)
    -> VE_Vor_Einschraenkung [VE_Vor_EinschraenkungRV]
VE_Vor_Einschraenkung
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BESCHWERDE_HAENGIG = @Value(Beschwerde_haengig)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    GUELTIG_BIS = @Value(Gueltig_bis)
    INKRAFTSETZUNG = @Value(Inkraftsetzung)
    KANTART = @Value(KantArt)
    LAERM_SCHEMA = $(LAERM_SCHEMA)
    NPL_SCHEMA = $(NPL_SCHEMA)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    THEMALAUFENDEAENDERUNG = @Value(ThemaLaufendeAenderung)
    TYP = @Value(Typ)
    UID_AMT = @Value(UID_AMT)
    VERBINDLICHKEIT = @Value(Verbindlichkeit)
    VORSCHRIFT = @Value(Vorschrift)
    WALDABST_SCHEMA = $(WALDABST_SCHEMA)
    XTF_ID = @Value(xtf_id)
    ZUSTAENDIGESTELLE = @Value(ZustaendigeStelle)
    EIGENTUMSBESCHRAENKUNG -> Aggregator
    FLAECHE -> FeatureHolder_5
    UEFL -> FeatureHolder_4
    HINVOR -> FeatureHolder
    VerwendeteAemter -> FeatureHolder_2

Bookmark: Dokumente / Amt
Note: Dokument
DM16NplBE.Nutzungsplanung.Dokument (reader ch.ehi.fme.Main_1)
    attributes: xtf_id xtf_char(200), Art_Doku xtf_char(255), Titel xtf_char(200), OffiziellerTitel xtf_char(200), Abkuerzung xtf_char(20), OffizielleNr xtf_char(20), Gemeinde xtf_int32, Dokument xtf_char(100), ZustaendigeStelle xtf_char(200)
    -> Dokument_vorbereiten [Dokument]
Note: Amt
DM16NplBE.Nutzungsplanung.Amt (reader ch.ehi.fme.Main_1)
    attributes: xtf_id xtf_char(200), Name xtf_char(200), UID_Amt xtf_char(15), AmtImWeb xtf_char(200)
    -> Amt_vorbereiten [Amt]
Note: HinweisWeitereDokumente
DM16NplBE.Nutzungsplanung.HinweisWeitereDokumente (reader ch.ehi.fme.Main_1)
    attributes: xtf_id xtf_char(200), Ursprung xtf_char(200), Hinweis xtf_char(200), ArtikelNr xtf_char(40), Ordnungsnummer xtf_int32
    -> HINWEIDOK-IDs_ersetzen [HinweisWeitereDokumente]

Bookmark: Gesetzliche Grundagen statisch verlinken (gemäss Handbuch DM16)
Note: Lärmschutzverordnung Bund als GEGR
AttributeCreator_9
    ATTR_LIST = VOR_OID,ch.admin.bk.sr.814.41
    -> UUIDGenerator_6
Note: Waldgesetz Bund als GEGR
AttributeCreator
    ATTR_LIST = VOR_OID,ch.admin.bk.sr.921.0
    -> UUIDGenerator_6
Note: Waldgesetz Kanton als GEGR
AttributeCreator_3
    ATTR_LIST = VOR_OID,ch.be.sk.bsg.921.11
    -> UUIDGenerator_6
Note: Waldverordnung Kanton als GEGR
AttributeCreator_4
    ATTR_LIST = VOR_OID,ch.be.sk.bsg.921.111
    -> UUIDGenerator_6
Note: Raumplanungsgesetz als GEGR
AttributeCreator_5
    ATTR_LIST = VOR_OID,ch.admin.bk.sr.700
    -> UUIDGenerator_6
Note: Baugesetz als GEGR
AttributeCreator_6
    ATTR_LIST = VOR_OID,ch.be.sk.bsg.721.0
    -> UUIDGenerator_6
Note: Bauverordnung als GEGR
AttributeCreator_7
    ATTR_LIST = VOR_OID,ch.be.sk.bsg.721.1
    -> UUIDGenerator_6
Note: BMBV als GEGR
AttributeCreator_8
    ATTR_LIST = VOR_OID,ch.be.sk.bsg.721.3
    -> UUIDGenerator_6
Note: HIV_ID
UUIDGenerator_6
    UUID_ATTR = HIV_ID
    -> AttributeRemover_17
AttributeRemover_17
    REMOVE_ATTRS = EIB_XTF_ID,STH_ID
    -> FeatureHolder_7
    -> AttributeRemover_6

Bookmark: AMT
Note: AMT (Excel)
AMT (reader XLSXR_1)
    attributes: AMT_OID char(20), AMT_NAME_DE char(73), AMT_NAME_FR char(73), AMT_AMTIMWEB_DE char(101), AMT_AMTIMWEB_FR char(102), AMT_LIEFEREINHEIT number(6,0), AMT_SPRACHE char(6)
    -> TestFilter_3
TestFilter_3
    DEFAULT_VALUE = <UNFILTERED>
    TEST_LIST = "BOOL_OP,OR,COMPOSITE_TEST,""""""<Unused>"""""",TEST_CLAUSE,TEST @Value(AMT_LIEFEREINHEIT) = $(LIEFEREINHEIT)",LIEFEREINHEIT
    LIEFEREINHEIT -> AMT (writer ORACLE8I_DB_1)
    LIEFEREINHEIT -> AttributeRenamer
Note: OEREB2.AMT
AMT (writer ORACLE8I_DB_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(6,0), AMT_LINE1 nvarchar(80), AMT_LINE2 nvarchar(80), AMT_STREET nvarchar(100), AMT_NUMBER nvarchar(7), AMT_POSTALCODE nvarchar(4), AMT_CITY nvarchar(60)
AttributeRenamer
    ATTR_TABLE:
      RENAME_SET_DEFAULT AMT_OID > id
      RENAME_SET_DEFAULT AMT_AMTIMWEB_DE > office_at_web
      RENAME_SET_DEFAULT AMT_LIEFEREINHEIT > liefereinheit
    -> JSONTemplater_4 [ROOT]
Note: Name-Attribut als JSON-String / aufbauen.
JSONTemplater_4
    RESULT_ATTRIBUTE = name
    ROOT_QUERY_EXPR:
      {
          "fr": fme:get-attribute("AMT_NAME_FR"),
          "de": fme:get-attribute("AMT_NAME_DE")
      }
    VISIBLE_QUERY_VALIDATE = Yes
    -> AttributeKeeper
AttributeKeeper
    KEEP_ATTRS = liefereinheit,office_at_web,name,id
    -> office (writer POSTGRES_2)
    -> office (writer POSTGRES_2)
    -> office (writer POSTGRES_2)
office (writer POSTGRES_2)
    attributes: id varchar(80),PrimaryKey, name json, office_at_web varchar(80), uid varchar(12), line1 varchar(80), line2 varchar(80), street varchar(80), number varchar(80), postal_code int4, city varchar(80), liefereinheit int4
office (writer POSTGRES_2)
    attributes: id varchar(80),PrimaryKey, name json, office_at_web varchar(80), uid varchar(12), line1 varchar(80), line2 varchar(80), street varchar(80), number varchar(80), postal_code int4, city varchar(80), liefereinheit int4
office (writer POSTGRES_2)
    attributes: id varchar(80),PrimaryKey, name json, office_at_web varchar(80), uid varchar(12), line1 varchar(80), line2 varchar(80), street varchar(80), number varchar(80), postal_code int4, city varchar(80), liefereinheit int4

Bookmark: Wertetabellen (sind bereits vorabgefüllt)
Note: NUPLA_VETHEMAT
NUPLA_VETHEMAT (writer GEODATABASE_SDE_2) [off]
    attributes: geodb_oid integer, OBJECTID integer, VE_THEMA smallint, BEZ_DE char(100), BEZ_FR char(100)
Note: NUPLA_VERBINDT
NUPLA_VERBINDT (writer GEODATABASE_SDE_2) [off]
    attributes: geodb_oid integer, OBJECTID integer, VERBINDLKT smallint, BEZ_DE char(100), BEZ_FR char(100)
Note: NUPLA_UEARTKTT
NUPLA_UEARTKTT (writer GEODATABASE_SDE_2) [off]
    attributes: geodb_oid integer, OBJECTID integer, KANTART smallint, BEZ_DE char(100), BEZ_FR char(100)
Note: NUPLA_GWBDBEST
NUPLA_GWBDBEST (writer GEODATABASE_SDE_2) [off]
    attributes: geodb_oid integer, OBJECTID integer, CODE smallint, BEZ_DE char(100), BEZ_FR char(100)
Note: NUPLA_ABSTDEFT
NUPLA_ABSTDEFT (writer GEODATABASE_SDE_2) [off]
    attributes: geodb_oid integer, OBJECTID integer, ABSTDEF smallint, BEZ_DE char(100), BEZ_FR char(100)
Note: NUPLA_STATUST
NUPLA_STATUST (writer GEODATABASE_SDE_2) [off]
    attributes: geodb_oid integer, OBJECTID integer, STATUS smallint, BEZ_DE char(100), BEZ_FR char(100)
Note: NUPLA_SCHUTZGT
NUPLA_SCHUTZGT (writer GEODATABASE_SDE_2) [off]
    attributes: geodb_oid integer, OBJECTID integer, SCHUTZG smallint, BEZ_DE char(100), BEZ_FR char(100)
Note: NUPLA_QUALIT
NUPLA_QUALIT (writer GEODATABASE_SDE_2) [off]
    attributes: geodb_oid integer, OBJECTID integer, QUALITAET smallint, BEZ_DE char(100), BEZ_FR char(100)
Note: NUPLA_BUNDESAT
NUPLA_BUNDESAT (writer GEODATABASE_SDE_2) [off]
    attributes: geodb_oid integer, OBJECTID integer, BUNDESART char(10), BEZ_DE char(150), BEZ_FR char(150)
Note: NUPLA_NZARTT
NUPLA_NZARTT (writer GEODATABASE_SDE_2) [off]
    attributes: geodb_oid integer, OBJECTID integer, NZ_ART smallint, BEZ_DE char(100), BEZ_FR char(100)
Note: NUPLA_NPZONET
NUPLA_NPZONET (writer GEODATABASE_SDE_2) [off]
    attributes: geodb_oid integer, OBJECTID integer, KANTART char(10), BEZ_DE char(100), BEZ_FR char(100)
Note: NUPLA_GWNATT
NUPLA_GWNATT (writer GEODATABASE_SDE_2) [off]
    attributes: geodb_oid integer, OBJECTID integer, GW_NAT smallint, BEZ_DE char(100), BEZ_FR char(100)
Note: NUPLA_BEDEUTT
NUPLA_BEDEUTT (writer GEODATABASE_SDE_2) [off]
    attributes: geodb_oid integer, OBJECTID integer, BEDEUT smallint, BEZ_DE char(100), BEZ_FR char(100)

Bookmark: Tabellen Erweiterung Stadt Bern (werden in anderem Script abgefüllt)
Note: NUPLA_UNBET
NUPLA_UNBET (writer GEODATABASE_SDE_2) [off]
    attributes: geodb_oid integer, OBJECTID integer, UNBESCHR smallint, BEZ_DE char(100), BEZ_FR char(100)
Note: NUPLA_GNBAUWS
NUPLA_GNBAUWS (writer GEODATABASE_SDE_2) [off]
    attributes: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
Note: NUPLA_ABGRZ
NUPLA_ABGRZ (writer GEODATABASE_SDE_2) [off]
    attributes: geodb_oid integer, OBJECTID integer, BFSNR smallint, NAME char(50), ART char(30), DARST_C char(5), SHAPE.LEN double
Note: NUPLA_BWTYPT
NUPLA_BWTYPT (writer GEODATABASE_SDE_2) [off]
    attributes: geodb_oid integer, OBJECTID integer, BWTYP smallint, BEZ_DE char(100), BEZ_FR char(100)
Note: NUPLA_GNNUTZBK
NUPLA_GNNUTZBK (writer GEODATABASE_SDE_2) [off]
    attributes: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

Bookmark: Deaktiviert, da in diesem Fall nie abgefüllt
Note: OEREB2.ARTIKEL
ARTIKEL (writer ORACLE8I_DB_1) [off]
    attributes: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
Note: OEREB2.HINWEIDOK
HINWEIDOK (writer ORACLE8I_DB_1) [off]
    attributes: HWD_ID nvarchar(128), HWD_XTF_ID nvarchar(128), HWD_LIEFEREINHEIT number(6,0), HWD_ARTNR nvarchar(255), VOR_OIDURSPRUNG nvarchar(128), VOR_OIDHINWEIS nvarchar(128)

FME custom transformer NH_NaturHeimatSchutz

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- DATENVERWALTUNGSSTELLE = @Value(Datenverwaltungsstelle)   # Datenverwaltungsstelle
- ZUSTAENDIGESTELLE = @Value(ZustaendigeStelle)   # ZustaendigeStelle
- QUALITAET = @Value(Qualitaet)   # Qualitaet
- TYP = @Value(Typ)   # Typ
- ORI = @Value(Ori)   # Ori
- BEDEUTUNG = @Value(Bedeutung)   # Bedeutung
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- SCHUTZGRAD = @Value(Schutzgrad)   # Schutzgrad
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

NH_FlaechenelementNHS (input)
    -> AttributeKeeper
AttributeKeeper
    KEEP_ATTRS = Objekt,Beschrieb,xtf_id,Qualitaet,Inkraftsetzung,Genehmigung
    -> UUIDGenerator
Note: FLA_OID
UUIDGenerator
    UUID_ATTR = FLA_OID
    -> AttributeRenamer_4
AttributeRenamer_4
    ATTR_LIST = xtf_id,FLA_XTF_ID,""
    -> FeatureMerger [REQUESTOR]
NH_LinienelementNHS (input)
    -> AttributeKeeper_2
AttributeKeeper_2
    KEEP_ATTRS = Objekt,Beschrieb,xtf_id,Qualitaet,Inkraftsetzung,Genehmigung
    -> UUIDGenerator_2
Note: LIN_OID
UUIDGenerator_2
    UUID_ATTR = LIN_OID
    -> AttributeRenamer_5
AttributeRenamer_5
    ATTR_LIST = xtf_id,LIN_XTF_ID,""
    -> FeatureMerger [REQUESTOR]
NH_PunktelementNHS (input)
    -> AttributeKeeper_3
AttributeKeeper_3
    KEEP_ATTRS = Objekt,Beschrieb,xtf_id,Qualitaet,Ori,Inkraftsetzung,Genehmigung
    -> UUIDGenerator_3
Note: PUN_OID
UUIDGenerator_3
    UUID_ATTR = PUN_OID
    -> AttributeRenamer_6
AttributeRenamer_6
    ATTR_LIST = xtf_id,PUN_XTF_ID,""
    -> FeatureMerger [REQUESTOR]
NH_NHSchutz (input)
    -> AttributeKeeper_4
AttributeKeeper_4
    KEEP_ATTRS = Bezeichnung,KantArt,xtf_id,Abkuerzung,Datenverwaltungsstelle,ZustaendigeStelle,Bedeutung,Bemerkung,DarstellungCode,Planbeschriftung,Verbindlichkeit,Schutzgrad
    -> UUIDGenerator_4
Note: EIB_OID
UUIDGenerator_4
    UUID_ATTR = EIB_OID
    -> AttributeRenamer
AttributeRenamer
    ATTR_LIST = xtf_id,EIB_XTF_ID,""
    -> AttributeFilter
Note: Nach Festlegung / Gemeinde filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,LINIENABK,"",DarstellungCode,DARST_C,"",Datenverwaltungsstelle,DATENVERW,"",ZustaendigeStelle,ZUSTAENDIG,"",Ori,ORI,""
    -> AttributeCreator
AttributeCreator
    ATTR_LIST = RVS_ID,@Value(EIB_OID),EIB_AUSSAGE_DE,@Value(BEZ),EIB_AUSSAGE_FR,@Value(BEZ),EIB_ARTCODE,@Value(LINIENABK),PUNKTABK,@Value(LINIENABK),ZONENABK,@Value(LINIENABK),EIB_SORT,@Evaluate(400+@int(@Value(KantArt))),RES_ID,1,FLA_PUBLIZIERTAB,@Value(EIB_PUBLIZIERTAB),LIN_PUBLIZIERTAB,@Value(EIB_PUBLIZIERTAB),PUN_PUBLIZIERTAB,@Value(EIB_PUBLIZIERTAB),schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: SCHUTZG mappen. / Interlis-Codelisten starten bei 0, / GeoDB-Wertetabellen bei 1!
AttributeValueMapper_4
    DIRECTION = Forward (Source To Destination)
    LUT = 0,1,1,2,2,3,3,4,4,5
    SRC = Schutzgrad
    VAL_ATTR = SCHUTZG
    -> AttributeValueMapper_5
Note: BEDEUT mappen. / Interlis-Codelisten starten bei 0, / GeoDB-Wertetabellen bei 1!
AttributeValueMapper_5
    DIRECTION = Forward (Source To Destination)
    LUT = 0,1,1,2,2,3,3,4,4,5
    SRC = Bedeutung
    VAL_ATTR = BEDEUT
    -> AttributeValueMapper
Note: KANTART mappen. / Interlis-Codelisten starten bei 0, / GeoDB-Wertetabellen bei 1!
AttributeValueMapper
    DIRECTION = Forward (Source To Destination)
    LUT = 0,37,1,38,2,39,3,40,4,41,5,42,6,43,7,44,8,45,9,46,10,47,11,48,12,49,13,50,14,51,15,52,16,53,17,54,18,55,19,56,20,57,21,58,22,59,23,60,24,61,25,62,26,63,27,64,28,65,29,66,30,67,31,68,32,69,33,70,34,71,35,72,36,73,37,74,38,75,39,76,40,77,41,78,42,79,43,80,44,81,45,82,46,83,47,84,48,85,49,86,50,87,51,88,52,89,53,90,54,91,55,92,56,93,57,94,58,95
    SRC = KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_5
AttributeKeeper_5
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_3
    JOIN -> AttributeKeeper_6
AttributeRemover_3
    REMOVE_ATTRS = xtf_id,Objekt,Qualitaet,Verbindlichkeit,KantArt,Bedeutung,Schutzgrad,_matched_records
    -> FeatureTypeFilter
FeatureTypeFilter
    ATTRIBUTES = <BLANK>,<UNFILTERED>,DM16NplBE.Nutzungsplanung.NH_FlaechenelementNHS,DM16NplBE.Nutzungsplanung.NH_LinienelementNHS,DM16NplBE.Nutzungsplanung.NH_PunktelementNHS
    DM16NplBE.Nutzungsplanung.NH_FlaechenelementNHS -> AttributeCreator_3
    DM16NplBE.Nutzungsplanung.NH_FlaechenelementNHS -> AttributeKeeper_8
    DM16NplBE.Nutzungsplanung.NH_LinienelementNHS -> AttributeCreator_5
    DM16NplBE.Nutzungsplanung.NH_LinienelementNHS -> AttributeKeeper_8
    DM16NplBE.Nutzungsplanung.NH_PunktelementNHS -> AttributeCreator_4
    DM16NplBE.Nutzungsplanung.NH_PunktelementNHS -> AttributeKeeper_8
AttributeCreator_3
    ATTR_LIST = STH_ID,13,DAR_OID,ch.be.bve.agi.npl.$(BFSNR).13
    -> AttributeKeeper_10
    -> AttributeKeeper_12
    -> AttributeKeeper_19
AttributeKeeper_12
    KEEP_ATTRS = DATENVERW,ZUSTAENDIG,BESCHRIEB,INKRAFT,GENEHM,BEZ,BEMERK,DARST_C,PLANBESCHR,RVS_ID,ZONENABK,QUALITAET,VERBINDLKT,SCHUTZG,BEDEUT,KANTART,BUNDESART
    -> UEFL (output)
UEFL (output)
AttributeKeeper_19
    KEEP_ATTRS = EIB_OID,FLA_OID,VERBINDLKT,RES_ID,FLA_XTF_ID,schema,FLA_PUBLIZIERTAB
    -> AttributeFilter_6
Note: Nur Festlegungen kommen / in die Transferstruktur
AttributeFilter_6
    ATTR_NAME = VERBINDLKT
    ATTR_VALUES = <EMPTY>,<MISSING>,<NULL>,<UNFILTERED>,3
    3 -> AttributeKeeper_20
AttributeKeeper_20
    KEEP_ATTRS = EIB_OID,FLA_OID,RES_ID,FLA_XTF_ID,schema,FLA_PUBLIZIERTAB
    -> FLAECHE (output)
FLAECHE (output)
AttributeCreator_5
    ATTR_LIST = STH_ID,14,DAR_OID,ch.be.bve.agi.npl.$(BFSNR).14
    -> AttributeKeeper_10
    -> AttributeKeeper_13
    -> AttributeKeeper_17
AttributeKeeper_13
    KEEP_ATTRS = DATENVERW,ZUSTAENDIG,BESCHRIEB,INKRAFT,GENEHM,BEZ,LINIENABK,BEMERK,DARST_C,PLANBESCHR,RVS_ID,QUALITAET,VERBINDLKT,SCHUTZG,BEDEUT,KANTART,BUNDESART
    -> UELN (output)
UELN (output)
AttributeKeeper_17
    KEEP_ATTRS = EIB_OID,LIN_PUBLIZIERTAB,LIN_XTF_ID,VERBINDLKT,RES_ID,LIN_OID,schema
    -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_18
AttributeKeeper_18
    KEEP_ATTRS = EIB_OID,LIN_PUBLIZIERTAB,LIN_XTF_ID,RES_ID,LIN_OID,schema
    -> LINIE (output)
LINIE (output)
AttributeCreator_4
    ATTR_LIST = STH_ID,15,DAR_OID,ch.be.bve.agi.npl.$(BFSNR).15
    -> AttributeKeeper_10
    -> AttributeKeeper_14
    -> AttributeKeeper_15
AttributeKeeper_10
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_11
AttributeKeeper_11
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_14
    KEEP_ATTRS = DATENVERW,INKRAFT,BEZ,GENEHM,RVS_ID,QUALITAET,ZUSTAENDIG,BESCHRIEB,KANTART,VERBINDLKT,ORI,DARST_C,SCHUTZG,BEDEUT,BEMERK,PUNKTABK,BUNDESART,PLANBESCHR
    -> UEPT (output)
UEPT (output)
AttributeKeeper_15
    KEEP_ATTRS = EIB_OID,PUN_OID,VERBINDLKT,PUN_XTF_ID,RES_ID,PUN_PUBLIZIERTAB,schema
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_16
AttributeKeeper_16
    KEEP_ATTRS = EIB_OID,PUN_OID,PUN_XTF_ID,RES_ID,PUN_PUBLIZIERTAB,schema
    -> PUNKT (output)
PUNKT (output)
AttributeKeeper_8
    KEEP_ATTRS = EIB_OID,VERBINDLKT,EIB_XTF_ID,schema
    -> FeatureMerger_2 [SUPPLIER]
AttributeKeeper_6
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
NH_NHSchutzRV (input)
    -> AttributeKeeper_7
AttributeKeeper_7
    KEEP_ATTRS = xtf_id,Typ,ArtikelNr,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_2
Note: Nur Festlegungen kommen / in die Transferstruktur
AttributeFilter_2
    ATTR_NAME = VERBINDLKT
    ATTR_VALUES = <EMPTY>,<MISSING>,<NULL>,<UNFILTERED>,3
    3 -> AttributeKeeper_9
AttributeKeeper_9
    KEEP_ATTRS = EIB_OID,Vorschrift,HIV_ARTNR,EIB_XTF_ID,schema
    -> HINVOR (output)
HINVOR (output)

FME custom transformer Dokument vorbereiten

Parameters:
- OFFIZIELLERTITEL = @Value(OffiziellerTitel)   # OffiziellerTitel
- TITEL = @Value(Titel)   # Titel
- XTF_ID = @Value(xtf_id)   # Xtf Id
- DOKUMENT = @Value(Dokument)   # Dokument
- ABKUERZUNG = @Value(Abkuerzung)   # Abkuerzung
- GEMEINDE = @Value(Gemeinde)   # Gemeinde
- ART_DOKU = @Value(Art_Doku)   # Art Doku
- ZUSTAENDIGESTELLE = @Value(ZustaendigeStelle)   # ZustaendigeStelle
- OFFIZIELLENR = @Value(OffizielleNr)   # OffizielleNr
- AMT_XTF_ID = @Value(AMT_XTF_ID)   # Amt Xtf Id
- AMT_ID = @Value(AMT_ID)   # Amt Id

Dokument (input)
    -> AttributeRemover_2
AttributeRemover_2
    REMOVE_ATTRS = AMT_XTF_ID,AMT_ID
    -> UUIDGenerator_5
Note: VOR_OID
UUIDGenerator_5
    UUID_ATTR = VOR_OID
    -> TimeStamper_2
TimeStamper_2
    FMT = FME Date (^Y^m^d)
    TIME_ATTR = VOR_PUBLIZIERTAB
    -> AttributeValueMapper
AttributeValueMapper
    DIRECTION = Forward (Source To Destination)
    LUT = 0,1,1,3
    SRC = Art_Doku
    VAL_ATTR = VOA_ID
    -> AttributeRenamer_4
AttributeRenamer_4
    ATTR_LIST = xtf_id,VOR_XTF_ID,,OffiziellerTitel,VOR_OFFIZIELLERTITEL_DE,,Abkuerzung,VOR_ABKUERZUNG_DE,,OffizielleNr,VOR_OFFIZIELLENR,
    -> AttributeCreator_4
AttributeCreator_4
    ATTR_LIST = VOR_TITEL_FR,@Value(VOR_OFFIZIELLERTITEL_DE),VOR_OFFIZIELLERTITEL_FR,@Value(VOR_OFFIZIELLERTITEL_DE),VOR_ABKUERZUNG_FR,@Value(VOR_ABKUERZUNG_DE),ZustaendigeStelle,@Value(ZustaendigeStelle),Dokument,@Value(Dokument),Gemeinde,@Value(Gemeinde),VOR_TITEL_DE,@Value(VOR_OFFIZIELLERTITEL_DE)
    -> PythonCaller
PythonCaller
    NEW_ATTRIBUTES = VOR_TEXTIMWEB_DE VOR_TEXTIMWEB_FR filecopy_source_dataset filecopy_dest_dataset
    PYTHONSOURCE:
      import fmeobjects
      import os

      def processFeature(feature):
          filename = feature.getAttribute('Dokument')
          if filename == 'Dekret_ueber_das_Normalbaureglement_NBRD.pdf' or  filename == 'Decret_concernant_le_reglement_norme_sur_les_constructions_DRN.pdf':
              feature.setAttribute('VOR_TEXTIMWEB_DE', 'https://www.belex.sites.be.ch/frontend/texts_of_law/565/download_pdf_file')
              feature.setAttribute('VOR_TEXTIMWEB_FR', 'https://www.belex.sites.be.ch/frontend/texts_of_law/565/download_pdf_file?locale=fr')
              feature.setAttribute('filecopy_source_dataset', 'Normalbaureglement')
              feature.setAttribute('filecopy_dest_dataset', 'Normalbaureglement')

          else:
              outputURL = FME_MacroValues['OUTPUT_RV_URL'] + filename

              inputFile = os.path.join(FME_MacroValues['INPUT_RV_DIR'], filename)
              inputFile = inputFile.replace('\\','/')

              outputDir = FME_MacroValues['OUTPUT_RV_DIR'].replace('\\','/')

              feature.setAttribute('VOR_TEXTIMWEB_DE', outputURL)
              feature.setAttribute('VOR_TEXTIMWEB_FR', outputURL)
              feature.setAttribute('filecopy_source_dataset', inputFile)
              feature.setAttribute('filecopy_dest_dataset', outputDir)
    PYTHONSYMBOL = processFeature
    -> FeatureMerger [REQUESTOR]
Amt (input)
    -> AttributeRemover
AttributeRemover
    REMOVE_ATTRS = OffiziellerTitel,ZustaendigeStelle,Titel,Abkuerzung,OffizielleNr,Gemeinde,xtf_id,Dokument,Art_Doku
    -> AttributeRenamer
AttributeRenamer
    ATTR_LIST = AMT_ID,ZUSTAENDIG,""
    -> FeatureMerger [SUPPLIER]
FeatureMerger
    IGNORE_NULLS = Yes
    JOIN_KEYS = @Value(ZustaendigeStelle) @Value(AMT_XTF_ID) AUTO
    MERGE_TYPE = Attributes Only
    PROCESS_DUPS = No
    SUPPLIERS_FIRST = No
    SUPPLIER_PREFIX_DUMMY = YES
    MERGED -> AttributeRemover_3
AttributeRemover_3
    REMOVE_ATTRS = Titel
    -> Alle_Dokumente (output)
Alle_Dokumente (output)

FME custom transformer HINWEIDOK-IDs ersetzen

Parameters:
- ARTIKELNR = @Value(ArtikelNr)   # ArtikelNr
- ORDNUNGSNUMMER = @Value(Ordnungsnummer)   # Ordnungsnummer
- VOR_OID = @Value(VOR_OID)   # Vor Oid
- URSPRUNG = @Value(Ursprung)   # Ursprung
- HINWEIS = @Value(Hinweis)   # Hinweis
- VOR_XTF_ID = @Value(VOR_XTF_ID)   # Vor Xtf Id

AlleDokumente (input)
    -> AttributeRemover_9
AttributeRemover_9
    REMOVE_ATTRS = Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset
    -> FeatureMerger_5 [SUPPLIER]
    -> FeatureMerger_6 [SUPPLIER]
HinweisWeitereDokumente (input)
    -> AttributeRenamer_5
AttributeRenamer_5
    ATTR_LIST = ArtikelNr,ARTIKELNR,"",Ordnungsnummer,ORDNNR,""
    -> AttributeRemover_7
AttributeRemover_7
    REMOVE_ATTRS = xtf_id
    -> FeatureMerger_5 [REQUESTOR]
FeatureMerger_5
    IGNORE_NULLS = Yes
    JOIN_KEYS = @Value(Ursprung) @Value(VOR_XTF_ID) AUTO
    MERGE_TYPE = Attributes Only
    PROCESS_DUPS = No
    SUPPLIERS_FIRST = No
    SUPPLIER_PREFIX_DUMMY = YES
    MERGED -> AttributeRenamer_6
AttributeRenamer_6
    ATTR_LIST = VOR_OID,VOR_OIDURSPRUNG,""
    -> AttributeRemover_12
AttributeRemover_12
    REMOVE_ATTRS = Ursprung,VOR_XTF_ID
    -> FeatureMerger_6 [REQUESTOR]
FeatureMerger_6
    IGNORE_NULLS = Yes
    JOIN_KEYS = @Value(Hinweis) @Value(VOR_XTF_ID) AUTO
    MERGE_TYPE = Attributes Only
    PROCESS_DUPS = No
    SUPPLIERS_FIRST = No
    SUPPLIER_PREFIX_DUMMY = YES
    MERGED -> AttributeRenamer_8
AttributeRenamer_8
    ATTR_LIST = VOR_OID,VOR_OIDHINWEIS,""
    -> AttributeRemover_13
AttributeRemover_13
    REMOVE_ATTRS = Hinweis,VOR_XTF_ID
    -> HINWEIDOK_ID_ersetzt (output)
HINWEIDOK_ID_ersetzt (output)

FME custom transformer UE_Abstandslinie

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- NUTZUNGSZIFFER_ART = @Value(Nutzungsziffer_Art)   # Nutzungsziffer Art
- DATENVERWALTUNGSSTELLE = @Value(Datenverwaltungsstelle)   # Datenverwaltungsstelle
- ZUSTAENDIGESTELLE = @Value(ZustaendigeStelle)   # ZustaendigeStelle
- GRUENFLAECHENZIFFER = @Value(Gruenflaechenziffer)   # Gruenflaechenziffer
- QUALITAET = @Value(Qualitaet)   # Qualitaet
- TYP = @Value(Typ)   # Typ
- NUTZUNGSZIFFER = @Value(Nutzungsziffer)   # Nutzungsziffer
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

UE_LinienelementAbstand (input)
    -> AttributeKeeper
AttributeKeeper
    KEEP_ATTRS = Objekt,Beschrieb,xtf_id,Qualitaet,Inkraftsetzung,Genehmigung
    -> UUIDGenerator
Note: LIN_OID
UUIDGenerator
    UUID_ATTR = LIN_OID
    -> AttributeRenamer_4
AttributeRenamer_4
    ATTR_LIST = xtf_id,LIN_XTF_ID,""
    -> FeatureMerger [REQUESTOR]
UE_Abstandslinie (input)
    -> AttributeKeeper_2
AttributeKeeper_2
    KEEP_ATTRS = Bezeichnung,KantArt,xtf_id,Abkuerzung,Nutzungsziffer_Art,Datenverwaltungsstelle,ZustaendigeStelle,Gruenflaechenziffer,Nutzungsziffer,Bemerkung,DarstellungCode,Planbeschriftung,Verbindlichkeit
    -> UUIDGenerator_2
Note: EIB_OID
UUIDGenerator_2
    UUID_ATTR = EIB_OID
    -> AttributeRenamer
AttributeRenamer
    ATTR_LIST = xtf_id,EIB_XTF_ID,""
    -> AttributeFilter
Note: Nach Festlegung / Gemeinde filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,LINIENABK,"",DarstellungCode,DARST_C,"",Nutzungsziffer,NZ,"",Gruenflaechenziffer,GRUENFZ,"",Datenverwaltungsstelle,DATENVERW,"",ZustaendigeStelle,ZUSTAENDIG,""
    -> AttributeCreator
AttributeCreator
    ATTR_LIST = RVS_ID,@Value(EIB_OID),EIB_AUSSAGE_DE,@Value(BEZ),EIB_AUSSAGE_FR,@Value(BEZ),EIB_ARTCODE,@Value(LINIENABK),EIB_SORT,@Evaluate(300+@int(@Value(KantArt))),RES_ID,1,STH_ID,14,LIN_PUBLIZIERTAB,@Value(EIB_PUBLIZIERTAB),DAR_OID,ch.be.bve.agi.npl.$(BFSNR).14,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper
Note: KANTART mappen. / Interlis-Codelisten starten bei 0, / GeoDB-Wertetabellen bei 1!
AttributeValueMapper
    DIRECTION = Forward (Source To Destination)
    LUT = 0,23,1,24,2,25,3,26,4,28,5,29,6,30,7,31,8,32,9,33,10,34,11,35,12,36
    SRC = KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_3
AttributeKeeper_3
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_3
    JOIN -> AttributeKeeper_4
AttributeRemover_3
    REMOVE_ATTRS = xtf_id,Objekt,Qualitaet,Verbindlichkeit,KantArt,Nutzungsziffer_Art,_matched_records
    -> AttributeFilter_2
AttributeFilter_2
    ATTR_NAME = KANTART
    ATTR_VALUES = <EMPTY>,<MISSING>,<NULL>,<UNFILTERED>,28
    <UNFILTERED> -> AttributeKeeper_5
    <UNFILTERED> -> AttributeKeeper_8
    <UNFILTERED> -> AttributeKeeper_10
    <UNFILTERED> -> AttributeKeeper_12
    28 -> AttributeCreator_3
AttributeKeeper_10
    KEEP_ATTRS = DATENVERW,ZUSTAENDIG,BESCHRIEB,INKRAFT,GENEHM,BEZ,LINIENABK,GRUENFZ,NZ,BEMERK,DARST_C,PLANBESCHR,RVS_ID,QUALITAET,VERBINDLKT,NZ_ART,KANTART,BUNDESART
    -> UELN (output)
UELN (output)
AttributeCreator_3
    ATTR_LIST = STH_ID,170,DAR_OID,ch.be.bve.agi.npl.$(BFSNR).170,schema,$(WALDABST_SCHEMA)
    -> AttributeKeeper_8
    -> AttributeKeeper_11
    -> AttributeKeeper_12
    -> AttributeKeeper_5
AttributeKeeper_8
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_9
AttributeKeeper_9
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_12
    KEEP_ATTRS = EIB_OID,LIN_PUBLIZIERTAB,LIN_XTF_ID,VERBINDLKT,RES_ID,LIN_OID,schema
    -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_13
AttributeKeeper_13
    KEEP_ATTRS = EIB_OID,LIN_PUBLIZIERTAB,LIN_XTF_ID,RES_ID,LIN_OID,schema
    -> LINIE (output)
LINIE (output)
AttributeKeeper_5
    KEEP_ATTRS = EIB_OID,VERBINDLKT,EIB_XTF_ID,schema
    -> FeatureMerger_2 [SUPPLIER]
AttributeKeeper_11
    KEEP_ATTRS = DATENVERW,ZUSTAENDIG,BESCHRIEB,INKRAFT,GENEHM,BEZ,LINIENABK,GRUENFZ,NZ,BEMERK,DARST_C,PLANBESCHR,RVS_ID,QUALITAET,VERBINDLKT,NZ_ART,KANTART,BUNDESART
    -> UEWAABL (output)
UEWAABL (output)
AttributeKeeper_4
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
UE_AbstandslinieRV (input)
    -> AttributeKeeper_6
AttributeKeeper_6
    KEEP_ATTRS = xtf_id,Typ,ArtikelNr,Vorschrift
    -> AttributeRemover_5
AttributeRemover_5
    REMOVE_ATTRS = Objekt,Bezeichnung,KantArt,Beschrieb,xtf_id,Abkuerzung,Nutzungsziffer_Art,Datenverwaltungsstelle,ZustaendigeStelle,Gruenflaechenziffer,Qualitaet,Nutzungsziffer,Bemerkung,Inkraftsetzung,DarstellungCode,Planbeschriftung,Genehmigung,Verbindlichkeit
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_7
AttributeKeeper_7
    KEEP_ATTRS = EIB_OID,Vorschrift,HIV_ARTNR,EIB_XTF_ID,schema
    -> HINVOR (output)
HINVOR (output)

FME custom transformer GW_Gewaesser

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- PLANBESCHRIFTUNG = @Value(Planbeschriftung)   # Planbeschriftung
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- OBJEKT = @Value(Objekt)   # Objekt
- OEKOMORPH_NATUERLICHKEIT = @Value(Oekomorph_Natuerlichkeit)   # Oekomorph Natuerlichkeit
- TYP = @Value(Typ)   # Typ
- ZUSTAENDIGESTELLE = @Value(ZustaendigeStelle)   # ZustaendigeStelle
- GENEHMIGUNG = @Value(Genehmigung)   # Genehmigung
- BEMERKUNG = @Value(Bemerkung)   # Bemerkung
- BEZEICHNUNG = @Value(Bezeichnung)   # Bezeichnung
- ART = @Value(Art)   # Art
- KULTURHIST_BEDEUTUNG = @Value(Kulturhist_Bedeutung)   # Kulturhist Bedeutung
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

GW_FlaechenelementGew (input)
    -> AttributeKeeper
AttributeKeeper
    KEEP_ATTRS = xtf_id,Inkraftsetzung,Qualitaet,Objekt,Genehmigung
    -> UUIDGenerator
Note: FLA_OID
UUIDGenerator
    UUID_ATTR = FLA_OID
    -> AttributeRenamer_4
AttributeRenamer_4
    ATTR_LIST = xtf_id,FLA_XTF_ID,""
    -> FeatureMerger [REQUESTOR]
GW_LinienelementGew (input)
    -> AttributeKeeper_2
AttributeKeeper_2
    KEEP_ATTRS = xtf_id,Inkraftsetzung,Qualitaet,Objekt,Genehmigung
    -> UUIDGenerator_2
Note: LIN_OID
UUIDGenerator_2
    UUID_ATTR = LIN_OID
    -> AttributeRenamer_5
AttributeRenamer_5
    ATTR_LIST = xtf_id,LIN_XTF_ID,""
    -> FeatureMerger [REQUESTOR]
GW_Gewaesser (input)
    -> AttributeKeeper_3
AttributeKeeper_3
    KEEP_ATTRS = Verbindlichkeit,xtf_id,Planbeschriftung,Datenverwaltungsstelle,DarstellungCode,Oekomorph_Natuerlichkeit,ZustaendigeStelle,Bemerkung,Bezeichnung,Art,Kulturhist_Bedeutung
    -> UUIDGenerator_4
Note: EIB_OID
UUIDGenerator_4
    UUID_ATTR = EIB_OID
    -> AttributeRenamer
AttributeRenamer
    ATTR_LIST = xtf_id,EIB_XTF_ID,""
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",Planbeschriftung,PLANBESCHR,"",DarstellungCode,DARST_C,"",Datenverwaltungsstelle,DATENVERW,"",ZustaendigeStelle,ZUSTAENDIG,"",Bemerkung,BEMERK,""
    -> AttributeCreator
AttributeCreator
    ATTR_LIST = RVS_ID,@Value(EIB_OID),EIB_AUSSAGE_DE,@Value(BEZ),EIB_AUSSAGE_FR,@Value(BEZ),EIB_SORT,@Evaluate(600+@int(@Value(Art))),RES_ID,1,FLA_PUBLIZIERTAB,@Value(EIB_PUBLIZIERTAB),LIN_PUBLIZIERTAB,@Value(EIB_PUBLIZIERTAB),EIB_ARTCODE,,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: GW_NAT mappen. / Interlis-Codelisten starten bei 0, / GeoDB-Wertetabellen bei 1!
AttributeValueMapper_4
    DIRECTION = Forward (Source To Destination)
    LUT = 0,1,1,2,2,3,3,4,4,5,5,6
    SRC = Oekomorph_Natuerlichkeit
    VAL_ATTR = GW_NAT
    -> AttributeValueMapper_5
Note: GW_BED mappen. / Interlis-Codelisten starten bei 0, / GeoDB-Wertetabellen bei 1!
AttributeValueMapper_5
    DIRECTION = Forward (Source To Destination)
    LUT = 0,1,1,2,2,3
    SRC = Kulturhist_Bedeutung
    VAL_ATTR = GW_BED
    -> AttributeValueMapper
Note: ART mappen. / Interlis-Codelisten starten bei 0, / GeoDB-Wertetabellen bei 1!
AttributeValueMapper
    DIRECTION = Forward (Source To Destination)
    LUT = 0,0,1,1
    SRC = Art
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_4
AttributeKeeper_4
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_3
    JOIN -> AttributeKeeper_5
AttributeRemover_3
    REMOVE_ATTRS = xtf_id,Qualitaet,Objekt,Verbindlichkeit,Oekomorph_Natuerlichkeit,Art,Kulturhist_Bedeutung,_matched_records
    -> FeatureTypeFilter
FeatureTypeFilter
    ATTRIBUTES = <BLANK>,<UNFILTERED>,DM16NplBE.Nutzungsplanung.GW_FlaechenelementGew,DM16NplBE.Nutzungsplanung.GW_LinienelementGew
    DM16NplBE.Nutzungsplanung.GW_FlaechenelementGew -> AttributeCreator_3
    DM16NplBE.Nutzungsplanung.GW_FlaechenelementGew -> AttributeKeeper_8
    DM16NplBE.Nutzungsplanung.GW_LinienelementGew -> AttributeCreator_5
    DM16NplBE.Nutzungsplanung.GW_LinienelementGew -> AttributeKeeper_8
AttributeCreator_3
    ATTR_LIST = STH_ID,13,DAR_OID,ch.be.bve.agi.npl.$(BFSNR).13
    -> AttributeKeeper_9
    -> AttributeKeeper_11
    -> AttributeKeeper_13
AttributeKeeper_9
    KEEP_ATTRS = DATENVERW,ZUSTAENDIG,INKRAFT,GENEHM,PLANBESCHR,DARST_C,BEMERK,BEZ,RVS_ID,QUALITAET,VERBINDLKT,GW_NAT,GW_BED,KANTART,BUNDESART
    -> UEFL (output)
UEFL (output)
AttributeKeeper_13
    KEEP_ATTRS = EIB_OID,FLA_OID,VERBINDLKT,RES_ID,FLA_XTF_ID,schema,FLA_PUBLIZIERTAB
    -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_14
AttributeKeeper_14
    KEEP_ATTRS = EIB_OID,FLA_OID,RES_ID,FLA_XTF_ID,schema,FLA_PUBLIZIERTAB
    -> FLAECHE (output)
FLAECHE (output)
AttributeCreator_5
    ATTR_LIST = STH_ID,14,DAR_OID,ch.be.bve.agi.npl.$(BFSNR).14
    -> AttributeKeeper_10
    -> AttributeKeeper_11
    -> AttributeKeeper_15
AttributeKeeper_11
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_2
Note: Nur Festlegungen kommen / in die Transferstruktur
AttributeFilter_2
    ATTR_NAME = VERBINDLKT
    ATTR_VALUES = <EMPTY>,<MISSING>,<NULL>,<UNFILTERED>,3
    3 -> AttributeKeeper_12
AttributeKeeper_12
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_15
    KEEP_ATTRS = EIB_OID,LIN_PUBLIZIERTAB,LIN_XTF_ID,VERBINDLKT,RES_ID,LIN_OID,schema
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_16
AttributeKeeper_16
    KEEP_ATTRS = EIB_OID,LIN_PUBLIZIERTAB,LIN_XTF_ID,RES_ID,LIN_OID,schema
    -> LINIE (output)
LINIE (output)
AttributeKeeper_10
    KEEP_ATTRS = DATENVERW,ZUSTAENDIG,INKRAFT,GENEHM,PLANBESCHR,DARST_C,BEMERK,BEZ,RVS_ID,QUALITAET,VERBINDLKT,GW_NAT,GW_BED,KANTART,BUNDESART
    -> UELN (output)
UELN (output)
AttributeKeeper_8
    KEEP_ATTRS = EIB_OID,VERBINDLKT,EIB_XTF_ID,schema
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
GW_GewaesserRV (input)
    -> AttributeKeeper_6
AttributeKeeper_6
    KEEP_ATTRS = xtf_id,ArtikelNr,Typ,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_7
AttributeKeeper_7
    KEEP_ATTRS = EIB_OID,Vorschrift,HIV_ARTNR,EIB_XTF_ID,schema
    -> HINVOR (output)
HINVOR (output)

FME custom transformer HINWEIDOK flachdruecken

HINWEIDOK (input)
    -> InlineQuerier [HINWEIDOK]
Note: SQL-Query stammt aus dem / View VIW_VORCHAIN1 der / Verschnittfunktion
InlineQuerier
    QUERY_DEF:
      VIW_VORCHAIN1,SELECT HINWEIDOK.VOR_OIDURSPRUNG,
        HINWEIDOK.VOR_OIDHINWEIS,
        HINWEIDOK1.VOR_OIDHINWEIS AS VOR_OIDHINWEIS1,
        HINWEIDOK2.VOR_OIDHINWEIS AS VOR_OIDHINWEIS2
      FROM HINWEIDOK
      LEFT JOIN HINWEIDOK HINWEIDOK1
      ON HINWEIDOK.VOR_OIDHINWEIS = HINWEIDOK1.VOR_OIDURSPRUNG
      LEFT JOIN HINWEIDOK HINWEIDOK2
      ON HINWEIDOK1.VOR_OIDHINWEIS = HINWEIDOK2.VOR_OIDURSPRUNG,FIRST
    QUERY_SCHEMA = VIW_VORCHAIN1,VOR_OIDURSPRUNG,text,VOR_OIDHINWEIS,text,VOR_OIDHINWEIS1,text,VOR_OIDHINWEIS2,text
    TABLE_DEF = HINWEIDOK,ARTIKELNR,text,ORDNNR,text,VOR_OIDURSPRUNG,text,VOR_OIDHINWEIS,text
    VIW_VORCHAIN1 -> InlineQuerier_2 [VIW_VORCHAIN1]
Note: SQL-Query stammt aus dem / View VIW_VORCHAIN2 der / Verschnittfunktion
InlineQuerier_2
    QUERY_DEF:
      VIW_VORCHAIN2,  select "VOR_OIDURSPRUNG","OIDFROM","OIDTO" from
      (select
      VOR_OIDURSPRUNG ,VOR_OIDURSPRUNG oidfrom,  VOR_OIDHINWEIS oidto from VIW_VORCHAIN1
      union
      select
      VOR_OIDURSPRUNG,VOR_OIDHINWEIS, VOR_OIDHINWEIS1 from VIW_VORCHAIN1
      union
      select
      VOR_OIDURSPRUNG,VOR_OIDHINWEIS1, VOR_OIDHINWEIS2 from VIW_VORCHAIN1
      )
      where oidfrom is not null and
      oidto is not null;,FIRST
    QUERY_SCHEMA = VIW_VORCHAIN2,VOR_OIDURSPRUNG,text,oidfrom,text,oidto,text
    TABLE_DEF = VIW_VORCHAIN1,VOR_OIDURSPRUNG,text,VOR_OIDHINWEIS,text,VOR_OIDHINWEIS1,text,VOR_OIDHINWEIS2,text
    VIW_VORCHAIN2 -> AttributeRenamer_11
AttributeRenamer_11
    ATTR_LIST = oidto,VOR_OIDHINWEIS,""
    -> AttributeRemover_14
AttributeRemover_14
    REMOVE_ATTRS = oidfrom
    -> HINWEIDOK_flach (output)
HINWEIDOK_flach (output)

FME custom transformer GR_Gewaesserraum

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- OBJEKT = @Value(Objekt)   # Objekt
- TYP = @Value(Typ)   # Typ
- ABSTANDRECHTS = @Value(AbstandRechts)   # AbstandRechts
- ZUSTAENDIGESTELLE = @Value(ZustaendigeStelle)   # ZustaendigeStelle
- ABSTANDLINKS = @Value(AbstandLinks)   # AbstandLinks
- ABSTANDDEFINITION = @Value(AbstandDefinition)   # AbstandDefinition
- GENEHMIGUNG = @Value(Genehmigung)   # Genehmigung
- BEMERKUNG = @Value(Bemerkung)   # Bemerkung
- BEZEICHNUNG = @Value(Bezeichnung)   # Bezeichnung
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

GR_Gewaesserraumflaeche (input)
    -> AttributeKeeper
AttributeKeeper
    KEEP_ATTRS = xtf_id,Inkraftsetzung,Qualitaet,Objekt,Genehmigung
    -> UUIDGenerator
Note: FLA_OID
UUIDGenerator
    UUID_ATTR = FLA_OID
    -> AttributeCreator_3
AttributeCreator_3
    ATTR_LIST = KANTART,18
    -> AttributeRenamer_5
AttributeRenamer_5
    ATTR_LIST = xtf_id,FLA_XTF_ID,""
    -> FeatureMerger [REQUESTOR]
GR_Gewaesserraumlinie (input)
    -> AttributeKeeper_2
AttributeKeeper_2
    KEEP_ATTRS = xtf_id,Inkraftsetzung,Qualitaet,Objekt,AbstandRechts,AbstandLinks,AbstandDefinition,Genehmigung
    -> UUIDGenerator_2
Note: LIN_OID
UUIDGenerator_2
    UUID_ATTR = LIN_OID
    -> AttributeCreator_4
AttributeCreator_4
    ATTR_LIST = KANTART,27
    -> AttributeRenamer_4
AttributeRenamer_4
    ATTR_LIST = xtf_id,LIN_XTF_ID,""
    -> FeatureMerger [REQUESTOR]
GR_Gewaesserraum (input)
    -> AttributeKeeper_3
AttributeKeeper_3
    KEEP_ATTRS = Verbindlichkeit,xtf_id,Datenverwaltungsstelle,DarstellungCode,ZustaendigeStelle,Bemerkung,Bezeichnung
    -> UUIDGenerator_4
Note: EIB_OID
UUIDGenerator_4
    UUID_ATTR = EIB_OID
    -> AttributeRenamer
AttributeRenamer
    ATTR_LIST = xtf_id,EIB_XTF_ID,""
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",DarstellungCode,DARST_C,"",Datenverwaltungsstelle,DATENVERW,"",ZustaendigeStelle,ZUSTAENDIG,"",Bemerkung,BEMERK,"",AbstandLinks,ABSTLINKS,"",AbstandRechts,ABSTRECHTS,""
    -> AttributeCreator
AttributeCreator
    ATTR_LIST = RVS_ID,@Value(EIB_OID),EIB_AUSSAGE_DE,@Value(BEZ),EIB_AUSSAGE_FR,@Value(BEZ),EIB_SORT,700,RES_ID,1,FLA_PUBLIZIERTAB,@Value(EIB_PUBLIZIERTAB),LIN_PUBLIZIERTAB,@Value(EIB_PUBLIZIERTAB),EIB_ARTCODE,,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: ABSTDEF mappen. / Interlis-Codelisten starten bei 0, / GeoDB-Wertetabellen bei 1!
AttributeValueMapper_4
    DIRECTION = Forward (Source To Destination)
    LUT = 0,1,1,2,2,3
    SRC = AbstandDefinition
    VAL_ATTR = ABSTDEF
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_4
AttributeKeeper_4
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeKeeper_5
    JOIN -> AttributeRemover_3
AttributeRemover_3
    REMOVE_ATTRS = xtf_id,Qualitaet,Objekt,AbstandDefinition,Verbindlichkeit,_matched_records
    -> FeatureTypeFilter
FeatureTypeFilter
    ATTRIBUTES = <BLANK>,<UNFILTERED>,DM16NplBE.Nutzungsplanung.GR_Gewaesserraumflaeche,DM16NplBE.Nutzungsplanung.GR_Gewaesserraumlinie
    DM16NplBE.Nutzungsplanung.GR_Gewaesserraumflaeche -> AttributeCreator_5
    DM16NplBE.Nutzungsplanung.GR_Gewaesserraumflaeche -> AttributeKeeper_7
    DM16NplBE.Nutzungsplanung.GR_Gewaesserraumlinie -> AttributeCreator_6
    DM16NplBE.Nutzungsplanung.GR_Gewaesserraumlinie -> AttributeKeeper_7
AttributeCreator_5
    ATTR_LIST = STH_ID,12,DAR_OID,ch.be.bve.agi.npl.$(BFSNR).12
    -> AttributeKeeper_9
    -> AttributeKeeper_11
    -> AttributeKeeper_13
AttributeKeeper_11
    KEEP_ATTRS = DATENVERW,ZUSTAENDIG,INKRAFT,GENEHM,KANTART,DARST_C,BEMERK,BEZ,RVS_ID,QUALITAET,VERBINDLKT,BUNDESART
    -> UEFL (output)
UEFL (output)
AttributeKeeper_13
    KEEP_ATTRS = EIB_OID,FLA_OID,VERBINDLKT,RES_ID,FLA_XTF_ID,schema,FLA_PUBLIZIERTAB
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_14
AttributeKeeper_14
    KEEP_ATTRS = EIB_OID,FLA_OID,RES_ID,FLA_XTF_ID,schema,FLA_PUBLIZIERTAB
    -> FLAECHE (output)
FLAECHE (output)
AttributeCreator_6
    ATTR_LIST = STH_ID,14,DAR_OID,ch.be.bve.agi.npl.$(BFSNR).14
    -> AttributeKeeper_9
    -> AttributeKeeper_12
    -> AttributeKeeper_15
AttributeKeeper_9
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_10
AttributeKeeper_10
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_15
    KEEP_ATTRS = EIB_OID,LIN_PUBLIZIERTAB,LIN_XTF_ID,VERBINDLKT,RES_ID,LIN_OID,schema
    -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_16
AttributeKeeper_16
    KEEP_ATTRS = EIB_OID,LIN_PUBLIZIERTAB,LIN_XTF_ID,RES_ID,LIN_OID,schema
    -> LINIE (output)
LINIE (output)
AttributeKeeper_12
    KEEP_ATTRS = DATENVERW,ZUSTAENDIG,INKRAFT,GENEHM,KANTART,ABSTRECHTS,ABSTLINKS,DARST_C,BEMERK,BEZ,RVS_ID,QUALITAET,VERBINDLKT,ABSTDEF,BUNDESART
    -> UELN (output)
UELN (output)
AttributeKeeper_7
    KEEP_ATTRS = EIB_OID,VERBINDLKT,EIB_XTF_ID,schema
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
GR_GewaesserraumRV (input)
    -> AttributeKeeper_6
AttributeKeeper_6
    KEEP_ATTRS = xtf_id,ArtikelNr,Typ,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_2
Note: Nur Festlegungen kommen / in die Transferstruktur
AttributeFilter_2
    ATTR_NAME = VERBINDLKT
    ATTR_VALUES = <EMPTY>,<MISSING>,<NULL>,<UNFILTERED>,3
    3 -> AttributeKeeper_8
AttributeKeeper_8
    KEEP_ATTRS = EIB_OID,Vorschrift,HIV_ARTNR,EIB_XTF_ID,schema
    -> HINVOR (output)
HINVOR (output)

FME custom transformer VE_Vor_Einschraenkung

Parameters:
- TYP = @Value(Typ)   # Typ
- VORSCHRIFT = @Value(Vorschrift)   # Vorschrift
- ARTIKELNR = @Value(ArtikelNr)   # ArtikelNr
- XTF_ID = @Value(xtf_id)   # Xtf Id
- VERBINDLICHKEIT = @Value(Verbindlichkeit)   # Verbindlichkeit
- KANTART = @Value(KantArt)   # KantArt
- GUELTIG_BIS = @Value(Gueltig_bis)   # Gueltig Bis
- BESCHWERDE_HAENGIG = @Value(Beschwerde_haengig)   # Beschwerde Haengig
- ABKUERZUNG = @Value(Abkuerzung)   # Abkuerzung
- PLANBESCHRIFTUNG = @Value(Planbeschriftung)   # Planbeschriftung
- BEZEICHNUNG = @Value(Bezeichnung)   # Bezeichnung
- NUTZUNGSZIFFER = @Value(Nutzungsziffer)   # Nutzungsziffer
- NUTZUNGSZIFFER_ART = @Value(Nutzungsziffer_Art)   # Nutzungsziffer Art
- GRUENFLAECHENZIFFER = @Value(Gruenflaechenziffer)   # Gruenflaechenziffer
- BEMERKUNG = @Value(Bemerkung)   # Bemerkung
- THEMALAUFENDEAENDERUNG = @Value(ThemaLaufendeAenderung)   # ThemaLaufendeAenderung
- DARSTELLUNGCODE = @Value(DarstellungCode)   # DarstellungCode
- DATENVERWALTUNGSSTELLE = @Value(Datenverwaltungsstelle)   # Datenverwaltungsstelle
- ZUSTAENDIGESTELLE = @Value(ZustaendigeStelle)   # ZustaendigeStelle
- OBJEKT = @Value(Objekt)   # Objekt
- GENEHMIGUNG = @Value(Genehmigung)   # Genehmigung
- INKRAFTSETZUNG = @Value(Inkraftsetzung)   # Inkraftsetzung
- BESCHRIEB = @Value(Beschrieb)   # Beschrieb
- QUALITAET = @Value(Qualitaet)   # Qualitaet
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- BFSNR =   # BFS-Nummer
- GEODB_DATABASE =   # GeoDB-Database
- GEODB_USERNAME =   # GeoDB-Username
- GEODB_PASSWORD =   # GeoDB-Passwort
- LAERM_SCHEMA =
- NPL_SCHEMA =
- WALDABST_SCHEMA =

VE_Vor_Einschraenkung (input)
    -> AttributeKeeper
AttributeKeeper
    KEEP_ATTRS = xtf_id,Verbindlichkeit,KantArt,Gueltig_bis,Beschwerde_haengig,Abkuerzung,Planbeschriftung,Bezeichnung,Nutzungsziffer,Nutzungsziffer_Art,Gruenflaechenziffer,Bemerkung,ThemaLaufendeAenderung,DarstellungCode,Datenverwaltungsstelle,ZustaendigeStelle
    -> UUIDGenerator
Note: EIB_OID
UUIDGenerator
    UUID_ATTR = EIB_OID
    -> AttributeRenamer
AttributeRenamer
    ATTR_LIST = xtf_id,EIB_XTF_ID,""
    -> AttributeFilter
Note: Nach Festlegung / Gemeinde filtern. Hier / werden absichtlich / keine Hinweise importiert
AttributeFilter
    ATTR_NAME = Verbindlichkeit
    ATTR_VALUES = <EMPTY>,<MISSING>,<NULL>,<UNFILTERED>,2
    2 -> FeatureMerger [SUPPLIER]
VE_FlaechenelementEinschr (input)
    -> AttributeKeeper_3
AttributeKeeper_3
    KEEP_ATTRS = xtf_id,Objekt,Genehmigung,Inkraftsetzung,Beschrieb,Qualitaet
    -> UUIDGenerator_2
UUIDGenerator_2
    UUID_ATTR = FLA_OID
    -> AttributeRenamer_3
AttributeRenamer_3
    ATTR_LIST = xtf_id,FLA_XTF_ID,""
    -> FeatureMerger [REQUESTOR]
Note: Filterung der KantArt hier nicht nötig. / Es werden alle Arten importiert.
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,ZONENABK,"",DarstellungCode,DARST_C,"",Nutzungsziffer,NZ,"",Gruenflaechenziffer,GRUENFZ,"",Datenverwaltungsstelle,DATENVERW,"",ZustaendigeStelle,ZUSTAENDIG,"",KantArt,_kantart,"",Gueltig_bis,VE_GUELTIG,""
    -> AttributeCreator
Note: RES_ID wird absichtlich / auf 1 gesetzt. Mit 2 / funktioniert die Anzeige im / Auszug noch nicht.
AttributeCreator
    ATTR_LIST = RVS_ID,@Value(EIB_OID),EIB_AUSSAGE_DE,@Value(BEZ),EIB_AUSSAGE_FR,@Value(BEZ),EIB_ARTCODE,@Value(ZONENABK),EIB_SORT,@Evaluate(200+@int(@Value(_kantart))),RES_ID,1,STH_ID,13,FLA_PUBLIZIERTAB,@Value(EIB_PUBLIZIERTAB),DAR_OID,ch.be.bve.agi.npl.$(BFSNR).13,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper_4
Note: KANTART mappen. / Interlis-Codelisten starten bei 0, / GeoDB-Wertetabellen bei 1!
AttributeValueMapper_4
    DIRECTION = Forward (Source To Destination)
    LUT = 0,104,1,105,2,106,3,107
    SRC = _kantart
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> AttributeValueMapper
Note: VE_BESCHW mappen
AttributeValueMapper
    DIRECTION = Forward (Source To Destination)
    LUT = 0,1,1,2
    SRC = Beschwerde_haengig
    VAL_ATTR = VE_BESCHW
    -> AttributeValueMapper_5
Note: VE_THEMA mappen
AttributeValueMapper_5
    DIRECTION = Forward (Source To Destination)
    LUT = 0,1,1,2,2,3,3,4,4,5,5,6,6,7
    SRC = ThemaLaufendeAenderung
    VAL_ATTR = VE_THEMA
    -> InlineQuerier [ZONE]
AlleAemter (input)
    -> AttributeKeeper_4
AttributeKeeper_4
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeKeeper_5
    JOIN -> AttributeKeeper_6
    JOIN -> AttributeKeeper_7
    JOIN -> AttributeKeeper_9
    JOIN -> AttributeKeeper_10
AttributeKeeper_6
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_7
    KEEP_ATTRS = EIB_OID,FLA_OID,RES_ID,FLA_XTF_ID,schema,FLA_PUBLIZIERTAB
    -> FLAECHE (output)
FLAECHE (output)
AttributeKeeper_10
    KEEP_ATTRS = DATENVERW,ZUSTAENDIG,GENEHM,INKRAFT,BESCHRIEB,VE_GUELTIG,ZONENABK,PLANBESCHR,BEZ,NZ,GRUENFZ,BEMERK,DARST_C,RVS_ID,QUALITAET,VERBINDLKT,NZ_ART,KANTART,BUNDESART,VE_BESCHW,VE_THEMA
    -> UEFL (output)
UEFL (output)
AttributeKeeper_9
    KEEP_ATTRS = EIB_OID,EIB_XTF_ID,schema
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> VerwendeteAemter (output)
VerwendeteAemter (output)
VE_Vor_EinschraenkungRV (input)
    -> AttributeKeeper_2
AttributeKeeper_2
    KEEP_ATTRS = Typ,Vorschrift,ArtikelNr
    -> AttributeRenamer_4
AttributeRenamer_4
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeKeeper_8
AttributeKeeper_8
    KEEP_ATTRS = EIB_OID,Vorschrift,HIV_ARTNR,EIB_XTF_ID,schema
    -> HINVOR (output)
HINVOR (output)

FME custom transformer Amt vorbereiten

Parameters:
- UID_AMT = @Value(UID_Amt)   # Uid Amt
- XTF_ID = @Value(xtf_id)   # Xtf Id
- AMTIMWEB = @Value(AmtImWeb)   # AmtImWeb
- NAME = @Value(Name)   # Name

Amt (input)
    -> UUIDGenerator_8
UUIDGenerator_8
    UUID_ATTR = AMT_ID
    -> AttributeRenamer_7
AttributeRenamer_7
    ATTR_LIST = Name,AMTNAME,"",AmtImWeb,AMTIMWEB,"",UID_Amt,UID_AMT,"",xtf_id,AMT_XTF_ID,""
    -> AMT (output)
AMT (output)

FME custom transformer GN_Grundnutzung

Parameters:
- GEODB_DATABASE =   # GeoDB-Database
- GEODB_USERNAME =   # GeoDB-Username
- GEODB_PASSWORD =   # GeoDB-Passwort
- BFSNR =   # BFS-Nummer
- BEZEICHNUNG = @Value(Bezeichnung)   # Bezeichnung
- KANTART = @Value(KantArt)   # KantArt
- BESCHRIEB = @Value(Beschrieb)   # Beschrieb
- BR_NUTZUNGSART = @Value(BR_Nutzungsart)   # Br Nutzungsart
- LAERMEMPFINDLICHKEIT = @Value(Laermempfindlichkeit)   # Laermempfindlichkeit
- XTF_ID = @Value(xtf_id)   # Xtf Id
- ABKUERZUNG = @Value(Abkuerzung)   # Abkuerzung
- NUTZUNGSZIFFER_ART = @Value(Nutzungsziffer_Art)   # Nutzungsziffer Art
- DATENVERWALTUNGSSTELLE = @Value(Datenverwaltungsstelle)   # Datenverwaltungsstelle
- ZUSTAENDIGESTELLE = @Value(ZustaendigeStelle)   # ZustaendigeStelle
- GRUENFLAECHENZIFFER = @Value(Gruenflaechenziffer)   # Gruenflaechenziffer
- QUALITAET = @Value(Qualitaet)   # Qualitaet
- TYP = @Value(Typ)   # Typ
- FLAECHENMASS = @Value(Flaechenmass)   # Flaechenmass
- ZONENTYPREF = @Value(ZonentypRef)   # ZonentypRef
- BR_NUTZUNGSMASS = @Value(BR_Nutzungsmass)   # Br Nutzungsmass
- NUTZUNGSZIFFER = @Value(Nutzungsziffer)   # Nutzungsziffer
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

GN_Zonentyp (input)
    -> AttributeKeeper
AttributeKeeper
    KEEP_ATTRS = Bezeichnung,KantArt,BR_Nutzungsart,xtf_id,Abkuerzung,Nutzungsziffer_Art,Datenverwaltungsstelle,ZustaendigeStelle,Gruenflaechenziffer,BR_Nutzungsmass,Nutzungsziffer,Bemerkung,DarstellungCode,Verbindlichkeit
    -> UUIDGenerator
Note: EIB_OID
UUIDGenerator
    UUID_ATTR = EIB_OID
    -> AttributeRenamer
AttributeRenamer
    ATTR_LIST = xtf_id,EIB_XTF_ID,""
    -> FeatureMerger [SUPPLIER]
GN_Grundzone (input)
    -> AttributeKeeper_2
AttributeKeeper_2
    KEEP_ATTRS = Beschrieb,Laermempfindlichkeit,xtf_id,Qualitaet,Flaechenmass,ZonentypRef,Bemerkung,Inkraftsetzung,Planbeschriftung,Genehmigung
    -> UUIDGenerator_2
Note: FLA_OID
UUIDGenerator_2
    UUID_ATTR = FLA_OID
    -> AttributeRenamer_4
GN_Grundzone_ZPP_UeO (input)
    -> AttributeFilter_5
Note: Fiktive Flächen rausfiltern
AttributeFilter_5
    ATTR_NAME = Beschrieb
    ATTR_VALUES = <EMPTY>,<MISSING>,<NULL>,<UNFILTERED>,fiktiv,Fiktiv,fictif,fictive
    <EMPTY> -> AttributeKeeper_3
    <MISSING> -> AttributeKeeper_3
    <NULL> -> AttributeKeeper_3
    <UNFILTERED> -> AttributeKeeper_3
AttributeKeeper_3
    KEEP_ATTRS = Beschrieb,Laermempfindlichkeit,xtf_id,Qualitaet,Flaechenmass,ZonentypRef,Bemerkung,Inkraftsetzung,Planbeschriftung,Genehmigung
    -> AttributeRenamer_4
AttributeRenamer_4
    ATTR_LIST = xtf_id,FLA_XTF_ID,""
    -> FeatureMerger [REQUESTOR]
FeatureMerger
    IGNORE_NULLS = Yes
    JOIN_KEYS = @Value(ZonentypRef) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,ZONENABK,"",DarstellungCode,DARST_C,"",BR_Nutzungsart,BR_NUTZART,"",BR_Nutzungsmass,BR_NMASS,"",Nutzungsziffer,NZ,"",Gruenflaechenziffer,GRUENFZ,"",Flaechenmass,FLMASS,"",Datenverwaltungsstelle,DATENVERW,"",ZustaendigeStelle,ZUSTAENDIG,""
    -> AttributeCreator
AttributeCreator
    ATTR_LIST = RVS_ID,@Value(EIB_OID),EIB_AUSSAGE_DE,@Value(BEZ),EIB_AUSSAGE_FR,@Value(BEZ),EIB_ARTCODE,@Value(ZONENABK),EIB_SORT,@Evaluate(100+@int(@Value(KantArt))),RES_ID,1,STH_ID,11,FLA_PUBLIZIERTAB,@Value(EIB_PUBLIZIERTAB),DAR_OID,ch.be.bve.agi.npl.$(BFSNR).11,schema,$(NPL_SCHEMA)
    -> DateFormatter
DateFormatter
    DATE_ATTR = INKRAFT,GENEHM
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper
Note: LAERMES mappen. / Inerlis-Codeliste startet bei 0, / die GeoDB-Wertetabelle hier / bei 7 (UEARTKTT)
AttributeValueMapper
    DIRECTION = Forward (Source To Destination)
    LUT = 0,7,1,8,2,9,3,10,4,11,5,12
    SRC = Laermempfindlichkeit
    VAL_ATTR = LAERMES
    -> AttributeValueMapper_4
Note: KANTART mappen. / Interlis-Codelisten starten bei 0, / GeoDB-Wertetabellen bei 1!
AttributeValueMapper_4
    DIRECTION = Forward (Source To Destination)
    LUT = 0,W1,1,W2,2,W3,3,W4,4,W5,5,W6plus,6,FH,7,M2,8,M3,9,M4,10,M5,11,M6plus,12,KS,13,KL,14,HT,15,WEZ,16,B_E,17,BH,18,A,19,ZOEN,20,SKI,21,ZSF,22,GR,23,GB,24,LWZ,25,ILW,26,AA,27,ZMN,28,UEO,29,ZPP,30,SBV,31,USP,32,Uebrige,33,VZ
    SRC = KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_NPZONET
    JOINED -> InlineQuerier [ZONE]
Alle_Aemter (input)
    -> AttributeKeeper_4
AttributeKeeper_4
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover
    JOIN -> AttributeKeeper_6
AttributeRemover
    REMOVE_ATTRS = xtf_id,Laermempfindlichkeit,Qualitaet,ZonentypRef,KantArt,Nutzungsziffer_Art,Verbindlichkeit,_matched_records
    -> FeatureTypeFilter
FeatureTypeFilter
    ATTRIBUTES = <BLANK>,<UNFILTERED>,DM16NplBE.Nutzungsplanung.GN_Grundzone_ZPP_UeO,DM16NplBE.Nutzungsplanung.GN_Grundzone
    DM16NplBE.Nutzungsplanung.GN_Grundzone_ZPP_UeO -> AttributeKeeper_13
    DM16NplBE.Nutzungsplanung.GN_Grundzone -> AttributeKeeper_7
    DM16NplBE.Nutzungsplanung.GN_Grundzone -> AttributeKeeper_9
    DM16NplBE.Nutzungsplanung.GN_Grundzone -> AttributeKeeper_10
    DM16NplBE.Nutzungsplanung.GN_Grundzone -> AttributeKeeper_14
AttributeKeeper_13
    KEEP_ATTRS = DATENVERW,ZUSTAENDIG,BESCHRIEB,FLMASS,BEMERK,INKRAFT,PLANBESCHR,GENEHM,BEZ,BR_NUTZART,ZONENABK,GRUENFZ,BR_NMASS,NZ,DARST_C,RVS_ID,QUALITAET,VERBINDLKT,NZ_ART,LAERMES,KANTART,BUNDESART
    -> AttributeFilter_6
Note: Nur Festlegungen Kanton und Gemeinde kommen / in die GNZPPUEO
AttributeFilter_6
    ATTR_NAME = VERBINDLKT
    ATTR_VALUES = <EMPTY>,<MISSING>,<NULL>,<UNFILTERED>,3,1
    3 -> GNZPPUEO (output)
    1 -> GNZPPUEO (output)
GNZPPUEO (output)
AttributeKeeper_14
    KEEP_ATTRS = DATENVERW,ZUSTAENDIG,BESCHRIEB,FLMASS,BEMERK,INKRAFT,PLANBESCHR,GENEHM,BEZ,BR_NUTZART,ZONENABK,GRUENFZ,BR_NMASS,NZ,DARST_C,RVS_ID,QUALITAET,VERBINDLKT,NZ_ART,LAERMES,KANTART,BUNDESART
    -> AttributeFilter_7
Note: Nur Festlegungen Gemeinde und Hinweise kommen / in die GNGRUZO
AttributeFilter_7
    ATTR_NAME = VERBINDLKT
    ATTR_VALUES = <EMPTY>,<MISSING>,<NULL>,<UNFILTERED>,3,4
    3 -> GNGRUZO (output)
    4 -> GNGRUZO (output)
GNGRUZO (output)
AttributeKeeper_7
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_2
Note: Nur Festlegungen Gemeinde kommen / in die Transferstruktur
AttributeFilter_2
    ATTR_NAME = VERBINDLKT
    ATTR_VALUES = <EMPTY>,<MISSING>,<NULL>,<UNFILTERED>,3
    3 -> AttributeKeeper_8
AttributeKeeper_8
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_10
    KEEP_ATTRS = EIB_OID,FLA_OID,VERBINDLKT,RES_ID,FLA_XTF_ID,schema,FLA_PUBLIZIERTAB
    -> AttributeFilter_3
Note: Nur Festlegungen Gemeinde kommen / in die Transferstruktur
AttributeFilter_3
    ATTR_NAME = VERBINDLKT
    ATTR_VALUES = <EMPTY>,<MISSING>,<NULL>,<UNFILTERED>,3
    3 -> AttributeKeeper_11
AttributeKeeper_11
    KEEP_ATTRS = EIB_OID,FLA_OID,RES_ID,FLA_XTF_ID,schema,FLA_PUBLIZIERTAB
    -> FLAECHE (output)
FLAECHE (output)
AttributeKeeper_9
    KEEP_ATTRS = EIB_OID,VERBINDLKT,EIB_XTF_ID,schema
    -> FeatureMerger_2 [SUPPLIER]
AttributeKeeper_6
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
GN_ZonentypRV (input)
    -> AttributeKeeper_5
AttributeKeeper_5
    KEEP_ATTRS = Typ,ArtikelNr,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_12
AttributeKeeper_12
    KEEP_ATTRS = EIB_OID,Vorschrift,HIV_ARTNR,EIB_XTF_ID,schema
    -> HINVOR (output)
HINVOR (output)

FME custom transformer UE_Ueberlagerung

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- NUTZUNGSZIFFER_ART = @Value(Nutzungsziffer_Art)   # Nutzungsziffer Art
- DATENVERWALTUNGSSTELLE = @Value(Datenverwaltungsstelle)   # Datenverwaltungsstelle
- ZUSTAENDIGESTELLE = @Value(ZustaendigeStelle)   # ZustaendigeStelle
- GRUENFLAECHENZIFFER = @Value(Gruenflaechenziffer)   # Gruenflaechenziffer
- QUALITAET = @Value(Qualitaet)   # Qualitaet
- TYP = @Value(Typ)   # Typ
- NUTZUNGSZIFFER = @Value(Nutzungsziffer)   # Nutzungsziffer
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

UE_FlaechenelementUeberl (input)
    -> AttributeKeeper
AttributeKeeper
    KEEP_ATTRS = Objekt,Beschrieb,xtf_id,Qualitaet,Inkraftsetzung,Genehmigung
    -> UUIDGenerator
Note: FLA_OID
UUIDGenerator
    UUID_ATTR = FLA_OID
    -> AttributeRenamer_4
AttributeRenamer_4
    ATTR_LIST = xtf_id,FLA_XTF_ID,""
    -> FeatureMerger [REQUESTOR]
UE_UeberlagerungZone (input)
    -> AttributeKeeper_2
AttributeKeeper_2
    KEEP_ATTRS = Bezeichnung,KantArt,xtf_id,Abkuerzung,Nutzungsziffer_Art,Datenverwaltungsstelle,ZustaendigeStelle,Gruenflaechenziffer,Nutzungsziffer,Bemerkung,DarstellungCode,Planbeschriftung,Verbindlichkeit
    -> UUIDGenerator_2
Note: EIB_OID
UUIDGenerator_2
    UUID_ATTR = EIB_OID
    -> AttributeRenamer
AttributeRenamer
    ATTR_LIST = xtf_id,EIB_XTF_ID,""
    -> AttributeFilter
Note: Nach Festlegung / Gemeinde filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,ZONENABK,"",DarstellungCode,DARST_C,"",Nutzungsziffer,NZ,"",Gruenflaechenziffer,GRUENFZ,"",Datenverwaltungsstelle,DATENVERW,"",ZustaendigeStelle,ZUSTAENDIG,""
    -> AttributeCreator
AttributeCreator
    ATTR_LIST = RVS_ID,@Value(EIB_OID),EIB_AUSSAGE_DE,@Value(BEZ),EIB_AUSSAGE_FR,@Value(BEZ),EIB_ARTCODE,@Value(ZONENABK),EIB_SORT,@Evaluate(200+@int(@Value(KantArt))),RES_ID,1,STH_ID,12,FLA_PUBLIZIERTAB,@Value(EIB_PUBLIZIERTAB),DAR_OID,ch.be.bve.agi.npl.$(BFSNR).12,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper_4
Note: KANTART mappen. / Interlis-Codelisten starten bei 0, / GeoDB-Wertetabellen bei 1!
Note: TODO: Mapping Gewässer
AttributeValueMapper_4
    DIRECTION = Forward (Source To Destination)
    LUT = 0,108,1,2,2,3,3,4,4,5,5,6,6,7,7,8,8,9,9,10,10,11,11,12,12,13,13,14,14,15,15,16,16,17,17,19
    SRC = KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_3
AttributeKeeper_3
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover
    JOIN -> AttributeKeeper_4
AttributeRemover
    REMOVE_ATTRS = xtf_id,Objekt,Qualitaet,Verbindlichkeit,KantArt,Nutzungsziffer_Art,_matched_records
    -> AttributeRangeFilter
AttributeRangeFilter
    IN_ATTR = KANTART
    LUT = 7,12,Laermempfindlichkeitsstufen,13,17,Gefahrengebiete
    Laermempfindlichkeitsstufen -> Attribute_Renamer_LES
    Gefahrengebiete -> Attribute_Renamer_Gefahren
    Gefahrengebiete -> AttributeKeeper_5
    Gefahrengebiete -> AttributeKeeper_13
    <UNFILTERED> -> AttributeKeeper_5
    <UNFILTERED> -> AttributeKeeper_9
    <UNFILTERED> -> AttributeKeeper_11
    <UNFILTERED> -> AttributeKeeper_13
Attribute_Renamer_LES: AttributeCreator
    ATTR_LIST = STH_ID,150,DAR_OID,ch.be.bve.agi.npl.$(BFSNR).150,schema,$(LAERM_SCHEMA)
    -> AttributeKeeper_8
    -> AttributeKeeper_9
    -> AttributeKeeper_11
    -> AttributeKeeper_5
AttributeKeeper_8
    KEEP_ATTRS = DATENVERW,ZUSTAENDIG,BESCHRIEB,INKRAFT,GENEHM,BEZ,ZONENABK,BEMERK,DARST_C,PLANBESCHR,RVS_ID,QUALITAET,VERBINDLKT,KANTART,BUNDESART
    -> UELARMES (output)
UELARMES (output)
AttributeKeeper_5
    KEEP_ATTRS = EIB_OID,VERBINDLKT,EIB_XTF_ID,schema
    -> FeatureMerger_2 [SUPPLIER]
Attribute_Renamer_Gefahren: AttributeCreator
    ATTR_LIST = STH_ID,12,DAR_OID,ch.be.bve.agi.npl.$(BFSNR).12
    -> AttributeKeeper_9
    -> AttributeKeeper_11
AttributeKeeper_9
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_2
Note: Nur Festlegungen kommen / in die Transferstruktur
AttributeFilter_2
    ATTR_NAME = VERBINDLKT
    ATTR_VALUES = <EMPTY>,<MISSING>,<NULL>,<UNFILTERED>,3
    3 -> AttributeKeeper_10
AttributeKeeper_10
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_11
    KEEP_ATTRS = EIB_OID,FLA_OID,VERBINDLKT,RES_ID,FLA_XTF_ID,schema,FLA_PUBLIZIERTAB
    -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_12
AttributeKeeper_12
    KEEP_ATTRS = EIB_OID,FLA_OID,RES_ID,FLA_XTF_ID,schema,FLA_PUBLIZIERTAB
    -> FLAECHE (output)
FLAECHE (output)
AttributeKeeper_13
    KEEP_ATTRS = DATENVERW,ZUSTAENDIG,BESCHRIEB,INKRAFT,GENEHM,BEZ,ZONENABK,GRUENFZ,NZ,BEMERK,DARST_C,PLANBESCHR,RVS_ID,QUALITAET,VERBINDLKT,NZ_ART,KANTART,BUNDESART
    -> UEFL (output)
UEFL (output)
AttributeKeeper_4
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
UE_UeberlagerungZoneRV (input)
    -> AttributeKeeper_6
AttributeKeeper_6
    KEEP_ATTRS = xtf_id,Typ,ArtikelNr,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_7
AttributeKeeper_7
    KEEP_ATTRS = EIB_OID,Vorschrift,HIV_ARTNR,EIB_XTF_ID,schema
    -> HINVOR (output)
HINVOR (output)

FME custom transformer WE_WegRoute

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- PLANBESCHRIFTUNG = @Value(Planbeschriftung)   # Planbeschriftung
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- SCHUTZGRAD = @Value(Schutzgrad)   # Schutzgrad
- OBJEKT = @Value(Objekt)   # Objekt
- TYP = @Value(Typ)   # Typ
- BEDEUTUNG = @Value(Bedeutung)   # Bedeutung
- ZUSTAENDIGESTELLE = @Value(ZustaendigeStelle)   # ZustaendigeStelle
- GENEHMIGUNG = @Value(Genehmigung)   # Genehmigung
- BEZEICHNUNG = @Value(Bezeichnung)   # Bezeichnung
- ART = @Value(Art)   # Art
- VORSCHRIFT = @Value(Vorschrift)   # Vorschrift
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- LAERM_SCHEMA =
- NPL_SCHEMA =
- WALDABST_SCHEMA =

WE_FlaechenelementWeg (input)
    -> AttributeKeeper
AttributeKeeper
    KEEP_ATTRS = xtf_id,Inkraftsetzung,Qualitaet,Objekt,Genehmigung
    -> UUIDGenerator
Note: FLA_OID
UUIDGenerator
    UUID_ATTR = FLA_OID
    -> AttributeRenamer_4
AttributeRenamer_4
    ATTR_LIST = xtf_id,FLA_XTF_ID,""
    -> FeatureMerger [REQUESTOR]
WE_LinienelementWeg (input)
    -> AttributeKeeper_2
AttributeKeeper_2
    KEEP_ATTRS = xtf_id,Inkraftsetzung,Qualitaet,Objekt,Genehmigung
    -> UUIDGenerator_2
Note: LIN_OID
UUIDGenerator_2
    UUID_ATTR = LIN_OID
    -> AttributeRenamer_5
AttributeRenamer_5
    ATTR_LIST = xtf_id,LIN_XTF_ID,""
    -> FeatureMerger [REQUESTOR]
WE_WegRoute (input)
    -> AttributeKeeper_3
AttributeKeeper_3
    KEEP_ATTRS = Verbindlichkeit,xtf_id,Planbeschriftung,Datenverwaltungsstelle,DarstellungCode,Schutzgrad,Bedeutung,ZustaendigeStelle,Bezeichnung,Art
    -> UUIDGenerator_4
Note: EIB_OID
UUIDGenerator_4
    UUID_ATTR = EIB_OID
    -> AttributeRenamer
AttributeRenamer
    ATTR_LIST = xtf_id,EIB_XTF_ID,""
    -> AttributeRemover_2
AttributeRemover_2
    REMOVE_ATTRS = ArtikelNr,Inkraftsetzung,Qualitaet,Objekt,Typ,Genehmigung
    -> AttributeFilter
Note: Nach Festlegung / Gemeinde filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",Planbeschriftung,PLANBESCHR,"",DarstellungCode,DARST_C,"",Datenverwaltungsstelle,DATENVERW,"",ZustaendigeStelle,ZUSTAENDIG,""
    -> AttributeCreator
AttributeCreator
    ATTR_LIST = RVS_ID,@Value(EIB_OID),EIB_AUSSAGE_DE,@Value(BEZ),EIB_AUSSAGE_FR,@Value(BEZ),EIB_SORT,@Evaluate(500+@int(@Value(Art))),RES_ID,1,FLA_PUBLIZIERTAB,@Value(EIB_PUBLIZIERTAB),LIN_PUBLIZIERTAB,@Value(EIB_PUBLIZIERTAB),EIB_ARTCODE,,schema,$(NPL_SCHEMA)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: SCHUTZG mappen. / Interlis-Codelisten starten bei 0, / GeoDB-Wertetabellen bei 1!
AttributeValueMapper_4
    DIRECTION = Forward (Source To Destination)
    LUT = 0,1,1,2,2,3,3,4,4,5
    SRC = Schutzgrad
    VAL_ATTR = SCHUTZG
    -> AttributeValueMapper_5
Note: BEDEUT mappen. / Interlis-Codelisten starten bei 0, / GeoDB-Wertetabellen bei 1!
AttributeValueMapper_5
    DIRECTION = Forward (Source To Destination)
    LUT = 0,1,1,2,2,3,3,4,4,5
    SRC = Bedeutung
    VAL_ATTR = BEDEUT
    -> AttributeValueMapper
Note: ART mappen. / Interlis-Codelisten starten bei 0, / GeoDB-Wertetabellen bei 1!
AttributeValueMapper
    DIRECTION = Forward (Source To Destination)
    LUT = 0,96,1,97,2,98,3,99,4,100,5,101,6,102,7,103
    SRC = Art
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_4
AttributeKeeper_4
    KEEP_ATTRS = AMT_XTF_ID,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_3
    JOIN -> AttributeKeeper_5
AttributeRemover_3
    REMOVE_ATTRS = xtf_id,Objekt,Qualitaet,Verbindlichkeit,Art,Bedeutung,Schutzgrad,_matched_records
    -> FeatureTypeFilter
FeatureTypeFilter
    ATTRIBUTES = <BLANK>,<UNFILTERED>,DM16NplBE.Nutzungsplanung.WE_FlaechenelementWeg,DM16NplBE.Nutzungsplanung.WE_LinienelementWeg
    DM16NplBE.Nutzungsplanung.WE_FlaechenelementWeg -> AttributeCreator_3
    DM16NplBE.Nutzungsplanung.WE_FlaechenelementWeg -> AttributeKeeper_7
    DM16NplBE.Nutzungsplanung.WE_LinienelementWeg -> AttributeCreator_5
    DM16NplBE.Nutzungsplanung.WE_LinienelementWeg -> AttributeKeeper_7
AttributeCreator_3
    ATTR_LIST = STH_ID,13,DAR_OID,ch.be.bve.agi.npl.$(BFSNR).13
    -> AttributeKeeper_9
    -> AttributeKeeper_11
    -> AttributeKeeper_13
AttributeKeeper_9
    KEEP_ATTRS = DATENVERW,ZUSTAENDIG,INKRAFT,GENEHM,PLANBESCHR,DARST_C,BEZ,RVS_ID,QUALITAET,VERBINDLKT,SCHUTZG,BEDEUT,KANTART,BUNDESART
    -> UEFL (output)
UEFL (output)
AttributeKeeper_13
    KEEP_ATTRS = EIB_OID,FLA_OID,VERBINDLKT,RES_ID,FLA_XTF_ID,schema,FLA_PUBLIZIERTAB
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_14
AttributeKeeper_14
    KEEP_ATTRS = EIB_OID,FLA_OID,RES_ID,FLA_XTF_ID,schema,FLA_PUBLIZIERTAB
    -> FLAECHE (output)
FLAECHE (output)
AttributeCreator_5
    ATTR_LIST = STH_ID,14,DAR_OID,ch.be.bve.agi.npl.$(BFSNR).14
    -> AttributeKeeper_10
    -> AttributeKeeper_11
    -> AttributeKeeper_15
AttributeKeeper_11
    KEEP_ATTRS = EIB_PUBLIZIERTAB,EIB_OID,EIB_SORT,STH_ID,VERBINDLKT,EIB_AUSSAGE_DE,EIB_AUSSAGE_FR,RES_ID,EIB_XTF_ID,schema,EIB_ARTCODE,DAR_OID
    -> AttributeFilter_2
Note: Nur Festlegungen kommen / in die Transferstruktur
AttributeFilter_2
    ATTR_NAME = VERBINDLKT
    ATTR_VALUES = <EMPTY>,<MISSING>,<NULL>,<UNFILTERED>,3
    3 -> AttributeKeeper_12
AttributeKeeper_12
    KEEP_ATTRS = EIB_PUBLIZIERTAB,EIB_OID,EIB_SORT,STH_ID,EIB_AUSSAGE_DE,EIB_AUSSAGE_FR,RES_ID,EIB_XTF_ID,schema,EIB_ARTCODE,DAR_OID
    -> EIGENTUMSBESCHRAENKUNG (output)
EIGENTUMSBESCHRAENKUNG (output)
AttributeKeeper_15
    KEEP_ATTRS = EIB_OID,LIN_PUBLIZIERTAB,LIN_XTF_ID,VERBINDLKT,RES_ID,LIN_OID,schema
    -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_16
AttributeKeeper_16
    KEEP_ATTRS = EIB_OID,LIN_PUBLIZIERTAB,LIN_XTF_ID,RES_ID,LIN_OID,schema
    -> LINIE (output)
LINIE (output)
AttributeKeeper_10
    KEEP_ATTRS = DATENVERW,ZUSTAENDIG,INKRAFT,GENEHM,PLANBESCHR,DARST_C,BEZ,RVS_ID,QUALITAET,VERBINDLKT,SCHUTZG,BEDEUT,KANTART,BUNDESART
    -> UELN (output)
UELN (output)
AttributeKeeper_7
    KEEP_ATTRS = EIB_OID,VERBINDLKT,EIB_XTF_ID,schema
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
WE_WegRouteRV (input)
    -> AttributeKeeper_6
AttributeKeeper_6
    KEEP_ATTRS = xtf_id,ArtikelNr,Typ,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_3
Note: Nur Festlegungen kommen / in die Transferstruktur
AttributeFilter_3
    ATTR_NAME = VERBINDLKT
    ATTR_VALUES = <EMPTY>,<MISSING>,<NULL>,<UNFILTERED>,3
    3 -> AttributeKeeper_8
AttributeKeeper_8
    KEEP_ATTRS = EIB_OID,Vorschrift,HIV_ARTNR,EIB_XTF_ID,schema
    -> HINVOR (output)
HINVOR (output)
