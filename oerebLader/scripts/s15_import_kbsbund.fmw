FME workspace s15_import_kbsbund.fmw
Startup Python:
      # -*- coding: latin-1 -*-
      import fmeobjects

      #=======================================================================================
      # Mehrsprachige Felder in INTERLIS2 behandeln
      def processMultilangFields(feature):

          multilangFields = feature.getAttribute('multilangfields').split(",")

          for mlField in multilangFields:
              content_de = ""
              content_fr = ""
              content_it = ""

              att_Language_list = feature.getAttribute(mlField + '{0}.LocalisedText{}.Language')
              att_Text_list = feature.getAttribute(mlField + '{0}.LocalisedText{}.Text')

              # wenn das Multilang-Feld nicht abgefüllt ist, soll es nicht bearbeitet werden
              if att_Language_list is not None:

                      for i in range(len(att_Language_list)):
                          if att_Language_list[i]=="de":
                              content_de = att_Text_list[i]
                          if att_Language_list[i]=="fr":
                              content_fr = att_Text_list[i]
                          if att_Language_list[i]=="it":
                              content_it = att_Text_list[i]

                      # Wenn der Text nur in einer Sprache vorhanden ist, wird er auch für die andere Sprache verwendet
                      if content_de == "":
                          content_de = content_fr
                      if content_de == "":
                          content_de = content_it
                      if content_fr == "":
                          content_fr = content_de
                      if content_fr == "":
                          content_fr = content_it

              feature.setAttribute(mlField + "_DE", content_de)
              feature.setAttribute(mlField + "_FR", content_fr)

Parameters:
- XTF_FILE =   # XTF-File
- USERNAME =   # Username
- PASSWORD =   # PASSWORD Passwort
- GPRCODE =   # Gprcode
- DATABASE =   # Database
- LOGFILE =   # Logfile
- MODELLABLAGE =   # Modellablage
- GEODB_PG_DATABASE =
- GEODB_PG_USERNAME =
- GEODB_PG_PASSWORD =
- GEODB_PG_HOST =
- GEODB_PG_PORT =
- XML_FILE =   # XML-File
- FCPOINT:   # Python Script
      fcname =  FME_MacroValues['GPRCODE'] + "_" + FME_MacroValues['GPRCODE'] + "P"
      return fcname
- FCPOLYGON:   # Python Script
      fcname =  FME_MacroValues['GPRCODE'] + "_" + FME_MacroValues['GPRCODE'] + "F"
      return fcname
- TBLDEPOTYP:   # Python Script
      tblname = FME_MacroValues['GPRCODE'] + "_DEPOTYP"
      return tblname
- TBLUNTERSM:   # Python Script
      tblname = FME_MacroValues['GPRCODE'] + "_UNTERSM"
      return tblname
- TBLSTATUS:   # Python Script
      tblname = FME_MacroValues['GPRCODE'] + "_STATUS"
      return tblname
- TBLSTAOTYP:   # Python Script
      tblname = FME_MacroValues['GPRCODE'] + "_STAOTYP"
      return tblname
- FCPOINT_PG = return FME_MacroValues['FCPOINT'].lower()   # Python Script
- FCPOLYGON_PG = return FME_MacroValues['FCPOLYGON'].lower()   # Python Script
- TBLDEPOTYP_PG = return FME_MacroValues['TBLDEPOTYP'].lower()   # Python Script
- TBLUNTERSM_PG = return FME_MacroValues['TBLUNTERSM'].lower()   # Python Script

Readers:
- ch.ehi.fme.Main_1: ch.ehi.fme.Main from $(XTF_FILE)
- ch.ehi.fme.Main_2: ch.ehi.fme.Main from $(XML_FILE)

Writers:
- GEODATABASE_SDE_1: GEODATABASE_SDE to sde
- POSTGIS_1: POSTGIS to $(GEODB_PG_DATABASE) in EPSG:2056

Note: KbS_LV95_V1_4.Belastete_Standorte.Belasteter_Standort
KbS_LV95_V1_4.Belastete_Standorte.Belasteter_Standort (reader ch.ehi.fme.Main_1)
    attributes: xtf_id xtf_char(200), Katasternummer xtf_buffer, URL_Standort xtf_char(1023), Geo_Lage_Polygon{}.xtf_class xtf_char(76), Geo_Lage_Polygon{}.Polygones{}.xtf_class xtf_char(76), Geo_Lage_Polygon{}.Polygones{}.Polygon xtf_buffer, Parzellenverweis{}.xtf_class xtf_char(76), Parzellenverweis{}.NBIdent xtf_buffer, Parzellenverweis{}.Parzellennummer xtf_buffer, EGRID{}.xtf_class xtf_char(76), EGRID{}.value xtf_buffer, Standorttyp xtf_char(255), InBetrieb xtf_boolean, Deponietyp{}.xtf_class xtf_char(76), Deponietyp{}.value xtf_char(255), Nachsorge xtf_boolean, Untersuchungsmassnahmen{}.xtf_class xtf_char(76), Untersuchungsmassnahmen{}.value xtf_char(255), StatusAltlV xtf_char(255), Ersteintrag xtf_date, LetzteAnpassung xtf_date, URL_KbS_Auszug xtf_char(1023), Bemerkung{}.xtf_class xtf_char(76), Bemerkung{}.LocalisedText{}.xtf_class xtf_char(76), Bemerkung{}.LocalisedText{}.Language xtf_char(255), Bemerkung{}.LocalisedText{}.Text xtf_buffer, ZustaendigkeitKataster xtf_char(200)
    -> AttributeRenamer
Note: Attribute passend umbenennen
AttributeRenamer
    ATTR_LIST = Katasternummer,KBSNUMMER,"",URL_KbS_Auszug,URLAUSZUG,"",Ersteintrag,ERSTEINTR,"",LetzteAnpassung,LETZTEANP,""
    -> StringCaseChanger
Note: Felder auf Kleinbuchstaben umstellen. / Weniger Probleme beim Mappen
StringCaseChanger
    ATTRCHOICE = Selected Attributes
    ATTRLIST = Standorttyp InBetrieb Nachsorge StatusAltlV
    CHANGE_TYPE = lowercase
    -> AttributeValueMapper
Note: STAOTYP mappen
AttributeValueMapper
    DIRECTION = Forward (Source To Destination)
    LUT = staotyp1,1,staotyp2,2,staotyp3,3,staotyp4,4
    SRC = Standorttyp
    VAL_ATTR = STAOTYP
    -> StatusAltlV1
Note: STATUS mappen
StatusAltlV1: AttributeValueMapper
    DIRECTION = Forward (Source To Destination)
    LUT = statusaltlv1,1,statusaltlv2,2,statusaltlv3,3,statusaltlv4,4,statusaltlv5,5,statusaltlv6,6
    SRC = StatusAltlV
    VAL_ATTR = STATUS
    -> AttributeValueMapper_2
Note: NACHSORGE mappen
AttributeValueMapper_2
    DIRECTION = Forward (Source To Destination)
    LUT = false,0,true,1
    SRC = Nachsorge
    VAL_ATTR = NACHSORGE
    -> AttributeValueMapper_3
Note: INBETRIEB mappen
AttributeValueMapper_3
    DIRECTION = Forward (Source To Destination)
    LUT = false,0,true,1
    SRC = InBetrieb
    VAL_ATTR = INBETRIEB
    -> AttributeRemover_3
AttributeRemover_3
    REMOVE_ATTRS = InBetrieb,Nachsorge
    -> AttributeCreator
AttributeCreator
    ATTR_LIST = multilangfields,Bemerkung
    -> PythonCaller
PythonCaller
    NEW_ATTRIBUTES = Bemerkung_DE Bemerkung_FR
    PYTHONSYMBOL = processMultilangFields
    -> AttributeRenamer_2
AttributeRenamer_2
    ATTR_LIST = Bemerkung_DE,BEMERK_D,"",Bemerkung_FR,BEMERK_F,""
    -> DateFormatter
Note: ERSTEINTR und / LETZTEANP formatieren
DateFormatter
    DATE_ATTR = ERSTEINTR,LETZTEANP
    FMT = ISO Date (%Y-%m-%d)
    INVALID_DATE_VALUE = _FME_NO_OP_
    SRCFMT = Unknown - Automatic Detection
    -> GeometryFilter
    -> AttributeRemover
    -> AttributeRemover_2
Note: Punkte herausfiltern
GeometryFilter
    BREAK_AGG = No
    GEOM_PORT_NAMES = Point
    POINT -> FeatureClass101 (writer GEODATABASE_SDE_1)
    POINT -> BulkAttributeRenamer_2
    <UNFILTERED> -> ListExploder_3
ListExploder_3
    ATTR_ACCUM_MODE = Merge Incoming List
    ATTR_CONFLICT_RES = Use Incoming List
    INDEX_ATTR = _element_index
    LIST_ATTR = Geo_Lage_Polygon{}
    ELEMENTS -> ListExploder_4
ListExploder_4
    ATTR_ACCUM_MODE = Merge Incoming List
    ATTR_CONFLICT_RES = Use Incoming List
    INDEX_ATTR = _element_index
    LIST_ATTR = Polygones{}
    ELEMENTS -> GeometryReplacer_2
GeometryReplacer_2
    KIND_LONG = FME Binary
    REMOVE_ATTRIBUTE = Yes
    SOURCE = @Value(Polygon)
    -> FeatureClass100 (writer GEODATABASE_SDE_1)
    -> BulkAttributeRenamer
Note: GEODB.KBSOEV_KBSOEVF
FeatureClass100 (writer GEODATABASE_SDE_1)
    attributes: KBSNUMMER char(100), STAOTYP smallint, INBETRIEB smallint, NACHSORGE smallint, STATUS smallint, ERSTEINTR char(255), LETZTEANP char(255), URLAUSZUG char(1024), BEMERK_D char(1024), BEMERK_F char(1024)
BulkAttributeRenamer
    ATTRCHOICE = All Attributes
    CASE_CHANGE_TYPE = lower
    MODE_CHOICE = RENAME
    PATTERN_ACTION_DISP = CASECHANGE
    -> kbsflug_kbsflugf (writer POSTGIS_1)
kbsflug_kbsflugf (writer POSTGIS_1)
    attributes: objectid int4, kbsnummer varchar(100), staotyp int2, inbetrieb int2, nachsorge int2, status int2, ersteintr varchar(255), letzteanp varchar(255), urlauszug varchar(255), bemerk_d varchar(255), bemerk_f varchar(255)
Note: GEODB.KBSOEV_KBSOEVP
FeatureClass101 (writer GEODATABASE_SDE_1)
    attributes: KBSNUMMER char(100), STAOTYP smallint, INBETRIEB smallint, NACHSORGE smallint, STATUS smallint, ERSTEINTR char(255), LETZTEANP char(255), URLAUSZUG char(1024), BEMERK_D char(1024), BEMERK_F char(1024)
BulkAttributeRenamer_2
    ATTRCHOICE = All Attributes
    CASE_CHANGE_TYPE = lower
    MODE_CHOICE = RENAME
    PATTERN_ACTION_DISP = CASECHANGE
    -> kbsflug_kbsflugp (writer POSTGIS_1)
kbsflug_kbsflugp (writer POSTGIS_1)
    attributes: objectid int4, kbsnummer varchar(100), staotyp int2, inbetrieb int2, nachsorge int2, status int2, ersteintr varchar(255), letzteanp varchar(255), urlauszug varchar(255), bemerk_d varchar(255), bemerk_f varchar(255)
Note: KbS_Basis_V1_4.Codelisten.Untersuchungsmassnahmen
KbS_Basis_V1_4.Codelisten.Untersuchungsmassnahmen_Definition (reader ch.ehi.fme.Main_2)
    attributes: xtf_id xtf_char(200), Code xtf_char(255), Definition{}.xtf_class xtf_char(76), Definition{}.LocalisedText{}.xtf_class xtf_char(76), Definition{}.LocalisedText{}.Language xtf_char(255), Definition{}.LocalisedText{}.Text xtf_buffer
    -> AttributeCreator_2
Note: GEODB.KBSOEV_UNTERSM
FeatureClass103 (writer GEODATABASE_SDE_1)
    attributes: KBSNUMMER char(100), MASSN_D char(100), MASSN_F char(100)
BulkAttributeRenamer_3
    ATTRCHOICE = All Attributes
    CASE_CHANGE_TYPE = lower
    MODE_CHOICE = RENAME
    PATTERN_ACTION_DISP = CASECHANGE
    -> kbsflug_untersm (writer POSTGIS_1)
kbsflug_untersm (writer POSTGIS_1)
    attributes: objectid int4, kbsnummer varchar(100), massn_d varchar(100), massn_f varchar(100)
Note: Nicht gematchte Codes sollte / es nicht geben.
Terminator_2
    MESSAGE = Nicht gematchte Untersuchungsmassnahme:
Note: KbS_Basis_V1_4.Codelisten.Deponietyp_Definition
KbS_Basis_V1_4.Codelisten.Deponietyp_Definition (reader ch.ehi.fme.Main_2)
    attributes: xtf_id xtf_char(200), Code xtf_char(255), Definition{}.xtf_class xtf_char(76), Definition{}.LocalisedText{}.xtf_class xtf_char(76), Definition{}.LocalisedText{}.Language xtf_char(255), Definition{}.LocalisedText{}.Text xtf_buffer
    -> AttributeCreator_3
Note: GEODB.KBSOEV_DEPOTYP
FeatureClass104 (writer GEODATABASE_SDE_1)
    attributes: KBSNUMMER char(100), DEPOTYP_D char(100), DEPOTYP_F char(100)
BulkAttributeRenamer_4
    ATTRCHOICE = All Attributes
    CASE_CHANGE_TYPE = lower
    MODE_CHOICE = RENAME
    PATTERN_ACTION_DISP = CASECHANGE
    -> kbsflug_depotyp (writer POSTGIS_1)
kbsflug_depotyp (writer POSTGIS_1)
    attributes: objectid int4, kbsnummer varchar(100), depotyp_d varchar(100), depotyp_f varchar(100)
Note: Nicht gematchte Codes sollte / es nicht geben.
Terminator_3
    MESSAGE = Nicht gematchter Deponietyp

Bookmark: NICHT RELEVANT
Note: KbS_LV95_V1_4.Belastete_Standorte.ZustaendigkeitKataster
KbS_LV95_V1_4.Belastete_Standorte.ZustaendigkeitKataster (reader ch.ehi.fme.Main_1) [off]
    attributes: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

Bookmark: Untersuchungsmassnahmen
AttributeRemover
    LIST_ATTRS = Parzellenverweis{} Parzellenverweis{}.xtf_class Deponietyp{}.value Parzellenverweis{}.NBIdent Deponietyp{}.xtf_class Bemerkung{}.LocalisedText{}.Language Bemerkung{}.LocalisedText{}.xtf_class EGRID{}.xtf_class EGRID{} Parzellenverweis{}.Parzellennummer Bemerkung{}.LocalisedText{} Bemerkung{} EGRID{}.value Bemerkung{}.LocalisedText{}.Text Deponietyp{} Bemerkung{}.xtf_class
    REMOVE_ATTRS = Geo_Lage_Punkt,INBETRIEB,ZustaendigkeitKataster,xtf_id,multilangfields,ERSTEINTR,BEMERK_F,URL_Standort,STATUS,URLAUSZUG,LETZTEANP,STAOTYP,StatusAltlV,BEMERK_D,NACHSORGE,Standorttyp
    -> ListExploder
ListExploder
    INDEX_ATTR = _element_index
    LIST_ATTR = Untersuchungsmassnahmen{}
    MODE = List Elements and Original Attributes
    LIST_FOUND -> FeatureMerger [REQUESTOR]
AttributeCreator_2
    ATTR_LIST = multilangfields,Definition
    -> PythonCaller_2
PythonCaller_2
    NEW_ATTRIBUTES = Definition_DE Definition_FR
    PYTHONSYMBOL = processMultilangFields
    -> AttributeRenamer_3
AttributeRenamer_3
    ATTR_LIST = Definition_DE,MASSN_D,"",Definition_FR,MASSN_F,""
    -> FeatureMerger [SUPPLIER]
FeatureMerger
    IGNORE_NULLS = Yes
    JOIN_KEYS = @Value(value) @Value(Code) AUTO
    MERGE_TYPE = Attributes Only
    PROCESS_DUPS = No
    SUPPLIERS_FIRST = No
    SUPPLIER_PREFIX_DUMMY = YES
    MERGED -> FeatureClass103 (writer GEODATABASE_SDE_1)
    MERGED -> BulkAttributeRenamer_3
    NOT_MERGED -> Terminator_2

Bookmark: Deponietyp
AttributeRemover_2
    LIST_ATTRS = Parzellenverweis{} Parzellenverweis{}.xtf_class Untersuchungsmassnahmen{} Parzellenverweis{}.NBIdent Untersuchungsmassnahmen{}.value Untersuchungsmassnahmen{}.xtf_class Bemerkung{}.LocalisedText{}.Language Bemerkung{}.LocalisedText{}.xtf_class EGRID{}.xtf_class EGRID{} Parzellenverweis{}.Parzellennummer Bemerkung{}.LocalisedText{} Bemerkung{} EGRID{}.value Bemerkung{}.LocalisedText{}.Text Bemerkung{}.xtf_class
    REMOVE_ATTRS = xtf_id,URL_Standort,Geo_Lage_Punkt,Standorttyp,InBetrieb,Nachsorge,StatusAltlV,ERSTEINTR,LETZTEANP,URLAUSZUG,ZustaendigkeitKataster,fme_type,STAOTYP,STATUS,NACHSORGE,INBETRIEB,multilangfields,BEMERK_DE,BEMERK_FR
    -> ListExploder_2
ListExploder_2
    INDEX_ATTR = _element_index
    LIST_ATTR = Deponietyp{}
    MODE = List Elements and Original Attributes
    LIST_FOUND -> FeatureMerger_2 [REQUESTOR]
AttributeCreator_3
    ATTR_LIST = multilangfields,Definition
    -> PythonCaller_3
PythonCaller_3
    NEW_ATTRIBUTES = Definition_DE Definition_FR
    PYTHONSYMBOL = processMultilangFields
    -> AttributeRenamer_4
AttributeRenamer_4
    ATTR_LIST = Definition_DE,DEPOTYP_D,"",Definition_FR,DEPOTYP_F,""
    -> FeatureMerger_2 [SUPPLIER]
FeatureMerger_2
    IGNORE_NULLS = Yes
    JOIN_KEYS = @Value(value) @Value(Code) AUTO
    MERGE_TYPE = Attributes Only
    PROCESS_DUPS = No
    SUPPLIERS_FIRST = No
    SUPPLIER_PREFIX_DUMMY = YES
    MERGED -> FeatureClass104 (writer GEODATABASE_SDE_1)
    MERGED -> BulkAttributeRenamer_4
    NOT_MERGED -> Terminator_3

Bookmark: WERTETABELLEN (sind bereits abgefüllt)
Note: NORM.KBSOEV_STAOTYP
FeatureClass102 (writer GEODATABASE_SDE_1) [off]
    attributes: geodb_oid integer, OBJECTID integer, STAOTYP smallint, STAOTYP_DE char(100), STAOTYP_FR char(100)
Note: KbS_Basis_V1_4.Codelisten.StatusAltlV_Definition
KbS_Basis_V1_4.Codelisten.StatusAltlV_Definition (reader ch.ehi.fme.Main_2) [off]
    attributes: xtf_id xtf_char(200), Code xtf_char(255), Definition{}.xtf_class xtf_char(76), Definition{}.LocalisedText{}.xtf_class xtf_char(76), Definition{}.LocalisedText{}.Language xtf_char(255), Definition{}.LocalisedText{}.Text xtf_buffer, Symbol xtf_buffer
Note: KbS_Basis_V1_4.Codelisten.Standorttyp_Definition
KbS_Basis_V1_4.Codelisten.Standorttyp_Definition (reader ch.ehi.fme.Main_2) [off]
    attributes: xtf_id xtf_char(200), Code xtf_char(255), Definition{}.xtf_class xtf_char(76), Definition{}.LocalisedText{}.xtf_class xtf_char(76), Definition{}.LocalisedText{}.Language xtf_char(255), Definition{}.LocalisedText{}.Text xtf_buffer
Note: NORM.KBSOEV_STATUS
FeatureClass1 (writer GEODATABASE_SDE_1) [off]
    attributes: geodb_oid integer, OBJECTID integer, STATUS smallint, STATUS_DE char(100), STATUS_FR char(100)
kbsflug_staotyp (writer POSTGIS_1) [off]
    attributes: objectid int4, staotyp int2, staotyp_d varchar(100), staotyp_f varchar(100)
kbsflug_status (writer POSTGIS_1) [off]
    attributes: objectid int4, status int2, status_d varchar(100), status_f varchar(100)
