FME workspace s68_update_nuplwald.fmw

Parameters:
- GEODB_DATABASE =   # GeoDB-Database
- GEODB_PASSWORD =   # GeoDB-Passwort
- GEODB_PG_DATABASE =
- GEODB_PG_HOST =
- GEODB_PG_PASSWORD =
- GEODB_PG_PORT =
- GEODB_PG_USERNAME =
- GEODB_USERNAME =   # GeoDB-Username
- OEREB_PG_DATABASE = sdf
- OEREB_PG_HOST =
- OEREB_PG_PASSWORD =
- OEREB_PG_PORT =
- OEREB_PG_USERNAME =
- OEREB2_DATABASE =   # Oereb-Database
- OEREB2_PASSWORD =   # Oereb-Passwort
- OEREB2_USERNAME =   # Oereb-Username
- LIEFEREINHEIT =
- BFSNR =
- LOGFILE =

Writers:
- ORACLE_NONSPATIAL_1: ORACLE_NONSPATIAL to $(GEODB_DATABASE)
- POSTGRES_1: POSTGRES to $(GEODB_PG_DATABASE)
- ORACLE_NONSPATIAL_2: ORACLE_NONSPATIAL to $(OEREB2_DATABASE)
- POSTGRES_2: POSTGRES to $(OEREB_PG_DATABASE)

Note: Jüngestes Genehmigungsdatum pro plr_id wird aus dem Geoprodukt ermittelt.
SQLCreator
    DATASET = $(GEODB_PG_DATABASE)
    EXPOSED_ATTRIBUTE_LIST = genehm_max,plr_id
    FORMAT = POSTGRES
    POSTGRES_HOST = $(GEODB_PG_HOST)
    POSTGRES_PASSWORD = $(GEODB_PG_PASSWORD)
    POSTGRES_PORT = $(GEODB_PG_PORT)
    POSTGRES_QUERY_FEATURE_TYPES_FOR_MERGE_FILTERS = Yes
    POSTGRES_READ_TIME_WITH_TIMEZONE = Yes
    POSTGRES_SCHEMAS_FOR_TABLE_LISTING = geodb
    POSTGRES_USER_NAME = $(GEODB_PG_USERNAME)
    SQL_STATEMENT = select rvs_id as plr_id, to_char(max(genehm), 'DD.MM.YYYY') as genehm_max from nuplwald_wfwagrz where bfsnr=$(BFSNR) group by rvs_id
    RESULT -> AttributeManager
AttributeManager
    ATTR_TABLE:
      SET_TO VOR_TITEL_DE = Waldfeststellungsverfügung vom @Value(genehm_max)
      SET_TO VOR_TITEL_FR = Décision de constatation de l'aire forestière du @Value(genehm_max)
      SET_TO VOR_OFFIZIELLERTITEL_DE = @Value(VOR_TITEL_DE)
      SET_TO VOR_OFFIZIELLERTITEL_FR = @Value(VOR_TITEL_FR)
      SET_TO TITEL = @Value(VOR_TITEL_DE)
      SET_TO OFFIZTITEL = @Value(VOR_TITEL_DE)
      SET_TO BFSNR = $(BFSNR)
      SET_TO VOR_LIEFEREINHEIT = $(LIEFEREINHEIT)
      SET_TO liefereinheit = $(LIEFEREINHEIT)
    -> JSONTemplater [ROOT]
JSONTemplater
    RESULT_ATTRIBUTE = title
    ROOT_QUERY_EXPR:
      {
          "fr": fme:get-attribute("VOR_TITEL_FR"),
          "de": fme:get-attribute("VOR_TITEL_DE")
      }
    VISIBLE_QUERY_VALIDATE = Yes
    -> AttributeManager_2
AttributeManager_2
    ATTR_TABLE:
      SET_TO official_title = @Value(title)
      SET_TO RVS_ID = @Value(plr_id)
      SET_TO EIB_OID = @Value(plr_id)
      SET_TO bfsnr = @Value(BFSNR)
      SET_TO rvs_id = @Value(RVS_ID)
      SET_TO titel = @Value(TITEL)
      SET_TO offiztitel = @Value(OFFIZTITEL)
      SET_TO ART = Rechtsvorschrift
      SET_TO art = @Value(ART)
      SET_TO VOA_ID = 1
      SET_TO document_type = LegalProvision
    -> AttributeKeeper
    -> AttributeKeeper_2
    -> AttributeKeeper_3
    -> AttributeKeeper_4
AttributeKeeper
    KEEP_ATTRS = BFSNR,ART,TITEL,RVS_ID,OFFIZTITEL
    -> NUPLWALD_WALDRVST (writer ORACLE_NONSPATIAL_1)
Note: Geoprodukt Oracle
NUPLWALD_WALDRVST (writer ORACLE_NONSPATIAL_1)
    attributes: BFSNR number(3,0), RVS_ID nvarchar(100), TITEL nvarchar(200), OFFIZTITEL nvarchar(200), ART nvarchar(40)
AttributeKeeper_2
    KEEP_ATTRS = rvs_id,titel,art,offiztitel,bfsnr
    -> nuplwald_waldrvst (writer POSTGRES_1)
Note: Geoprodukt PostGIS
nuplwald_waldrvst (writer POSTGRES_1)
    attributes: bfsnr int2, rvs_id varchar(100), titel varchar(200), offiztitel varchar(200), art varchar(40)
AttributeKeeper_3
    KEEP_ATTRS = VOA_ID,VOR_OFFIZIELLERTITEL_FR,EIB_OID,VOR_TITEL_FR,VOR_TITEL_DE,VOR_LIEFEREINHEIT,VOR_OFFIZIELLERTITEL_DE
    -> DuplicateFilter
DuplicateFilter
    INPUT_ORDERED_CHOICE = No
    KEYATTR = VOA_ID VOR_OFFIZIELLERTITEL_FR EIB_OID VOR_TITEL_FR VOR_TITEL_DE VOR_LIEFEREINHEIT VOR_OFFIZIELLERTITEL_DE
    UNIQUE -> FeatureMerger [SUPPLIER]
AttributeKeeper_4
    KEEP_ATTRS = liefereinheit,document_type,official_title,title,plr_id
    -> FeatureMerger_2 [SUPPLIER]
Note: Alle infrage kommenden Dokumente aus der Transferstruktur Oracle holen.
SQLCreator_2
    DATASET = $(OEREB2_DATABASE)
    EXPOSED_ATTRIBUTE_LIST = VOR_OID,EIB_OID
    FORMAT = ORACLE_NONSPATIAL
    ORACLE_NONSPATIAL_PASSWORD = $(OEREB2_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(OEREB2_USERNAME)
    ORACLE_NONSPATIAL_USE_UNIFIED_DATE_ATTRS = YES
    SQL_STATEMENT = select e.eib_oid as EIB_OID, v.vor_oid as VOR_OID from eigentumsbeschraenkung e left join hinvor h on e.eib_oid=h.eib_oid left join vorschrift v on h.vor_oid=v.vor_oid where e.eib_liefereinheit=$(LIEFEREINHEIT) and voa_id=1
    RESULT -> FeatureMerger [REQUESTOR]
FeatureMerger
    ATTR_ACCUM_MODE = Merge Supplier
    ATTR_CONFLICT_RES = Use Requestor
    IGNORE_NULLS = No
    JOIN_KEYS = @Value(EIB_OID) @Value(EIB_OID) AUTO
    MERGE_TYPE = Attributes Only
    PROCESS_DUPS = NO
    REJECT_NULL_MISSING_KEYS = No
    SUPPLIERS_FIRST = No
    MERGED -> VORSCHRIFT (writer ORACLE_NONSPATIAL_2)
Note: Transferstruktur Oracle
VORSCHRIFT (writer ORACLE_NONSPATIAL_2)
    attributes: VOR_OID nvarchar(128), VOR_TITEL_DE nvarchar(200), VOR_TITEL_FR nvarchar(200), VOR_OFFIZIELLERTITEL_DE nvarchar(255), VOR_OFFIZIELLERTITEL_FR nvarchar(255), VOR_LIEFEREINHEIT number(6,0), VOA_ID number(10,0)
Note: Alle infrage kommenden Dokumente aus der Transferstruktur PostGIS holen.
SQLCreator_3
    DATASET = $(OEREB_PG_DATABASE)
    EXPOSED_ATTRIBUTE_LIST = id,plr_id
    FORMAT = POSTGRES
    POSTGRES_HOST = $(OEREB_PG_HOST)
    POSTGRES_PASSWORD = $(OEREB_PG_PASSWORD)
    POSTGRES_PORT = $(OEREB_PG_PORT)
    POSTGRES_QUERY_FEATURE_TYPES_FOR_MERGE_FILTERS = Yes
    POSTGRES_READ_TIME_WITH_TIMEZONE = Yes
    POSTGRES_SCHEMAS_FOR_TABLE_LISTING = forest_perimeters
    POSTGRES_USER_NAME = $(OEREB_PG_USERNAME)
    SQL_STATEMENT = select d.id id, e.id plr_id from forest_perimeters.public_law_restriction e left join forest_perimeters.public_law_restriction_document h on e.id=h.public_law_restriction_id left join forest_perimeters."document" d on h.document_id=d.id where e.liefereinheit=$(LIEFEREINHEIT) and d.document_type='LegalProvision'
    RESULT -> FeatureMerger_2 [REQUESTOR]
FeatureMerger_2
    ATTR_ACCUM_MODE = Merge Supplier
    ATTR_CONFLICT_RES = Use Requestor
    IGNORE_NULLS = No
    JOIN_KEYS = @Value(plr_id) @Value(plr_id) AUTO
    MERGE_TYPE = Attributes Only
    PROCESS_DUPS = NO
    REJECT_NULL_MISSING_KEYS = No
    SUPPLIERS_FIRST = No
    MERGED -> document (writer POSTGRES_2)
Note: Transferstruktur PostGIS
document (writer POSTGRES_2)
    attributes: document_type varchar(80), title json, official_title json, id varchar(80),PrimaryKey, liefereinheit int4,BTree
