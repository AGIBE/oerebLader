FME workspace s17_import_npl.fmw

Parameters:
- DATABASE =   # Database
- USERNAME =   # Username
- PASSWORD =   # Passwort
- BFSNR =   # BFS-Nummer
- LOGFILE =   # Logfile

Readers:
- GEODATABASE_SDE_1: GEODATABASE_SDE from sde
- GEODATABASE_SDE_2: GEODATABASE_SDE from sde

Writers:
- GEODATABASE_SDE_3: GEODATABASE_SDE to sde

Note: GEODB.NUPLA_UEWAABL
GEODB.NUPLA_UEWAABL (reader GEODATABASE_SDE_1)
    attributes: geodb_oid integer, OBJECTID integer, BFSNR smallint, GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, SHAPE.LEN double, RVS_ID char(100), GEMNAME char(50)
    -> AttributeRenamer_5
AttributeRenamer_5
    ATTR_LIST = VERBINDLKT,_verbindlkt,"",KANTART,_kantart,"",RVS_ID,REL_ID,"",GEMNAME,NAME,""
    -> Joiner_4
Note: VERBINDLKT joinen
Joiner_4
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeCreator
Note: KANTART fix setzen
AttributeCreator
    ATTR_LIST = KANTART,Wald-Baulinie
    -> AttributeRenamer_6
AttributeRenamer_6
    ATTR_LIST = VERBINDT_BEZ_DE,VERBINDLKT,""
    -> GEODB.NPL_UEWAAB (writer GEODATABASE_SDE_3)
Note: GEODB.NPL_UEWAAB
GEODB.NPL_UEWAAB (writer GEODATABASE_SDE_3)
    attributes: BFSNR smallint, NAME char(31), REL_ID char(100), VERBINDLKT char(100), KANTART char(100), LINIENABK char(12), LINIENCODE char(12)
Note: GEODB.NUPLA_UEFL
GEODB.NUPLA_UEFL (reader GEODATABASE_SDE_1)
    attributes: geodb_oid integer, OBJECTID integer, BFSNR smallint, RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, VE_GUELTIG date, VE_BESCHW smallint, VE_THEMA smallint, SHAPE.AREA double, SHAPE.LEN double,
      GEMNAME char(50)
    -> AttributeRenamer_8
AttributeRenamer_8
    ATTR_LIST = RVS_ID,REL_ID,"",VERBINDLKT,_verbindlkt,"",KANTART,_kantart,"",BESCHRIEB,_beschrieb,"",GEMNAME,NAME,""
    -> Joiner_5
Note: VERBINDLKT joinen
Joiner_5
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeRenamer_9
AttributeRenamer_9
    ATTR_LIST = VERBINDT_BEZ_DE,VERBINDLKT,"",BEZ,BESCHRIEB,""
    -> TestFilter
Note: Aufteilung in Featureclasses
TestFilter
    TEST_LIST = BOOL_OP,OR,COMPOSITE_TEST,<Unused>,TEST_CLAUSE,"TEST @Value(_kantart) IN 104-107",VEFE,BOOL_OP,OR,COMPOSITE_TEST,<Unused>,TEST_CLAUSE,"TEST @Value(_kantart) IN 2,3,4,5,6,18,19,108",UEUZ,BOOL_OP,OR,COMPOSITE_TEST,<Unused>,TEST_CLAUSE,"TEST @Value(_kantart) IN 13-17",GEFF,BOOL_OP,OR,COMPOSITE_TEST,<Unused>,TEST_CLAUSE,"TEST @Value(_kantart) IN 96-103",WEWRF,BOOL_OP,OR,COMPOSITE_TEST,<Unused>,TEST_CLAUSE,"TEST @Value(_kantart) IN 0,1",GEGEWF,BOOL_OP,OR,COMPOSITE_TEST,<Unused>,TEST_CLAUSE,"TEST @Value(_kantart) IN 37-95",NHSF
    DEFAULT_VALUE = <UNFILTERED>
    UEUZ -> AttributeValueMapper_3
    GEFF -> AttributeCreator_2
    WEWRF -> AttributeValueMapper_5
    GEGEWF -> AttributeValueMapper_6
    NHSF -> AttributeValueMapper_7
    VEFE -> AttributeRenamer_14
AttributeRenamer_14
    ATTR_LIST = VE_GUELTIG,GUELTIGBIS,""
    -> AttributeValueMapper_20
AttributeValueMapper_20
    DIRECTION = Forward (Source To Destination)
    VAL_ATTR = KANTART
    LUT = 104,Beschwerde,105,sistiertes Gebiet,106,Laufende Änderung,107,Vorübergehende Einschränkung andere
    SRC = _kantart
    -> GEODB.NPL_VEFE (writer GEODATABASE_SDE_3)
GEODB.NPL_VEFE (writer GEODATABASE_SDE_3)
    attributes: BFSNR smallint, NAME char(31), REL_ID char(100), VERBINDLKT char(100), KANTART char(100), GUELTIGBIS date, BESCHRIEB char(80)
Note: KANTART UEUZ
AttributeValueMapper_3
    DIRECTION = Forward (Source To Destination)
    VAL_ATTR = KANTART
    LUT = 108,Gewässer,2,Wald,3,Überbauungsordnung,4,Überbauungsordnung ohne Art und Mass der baulichen Nutzung,5,Zone mit Planungspflicht,6,Verkehrsfläche im Siedlungsgebiet,18,Gewässerraumfläche,19,Weitere Überlagerung
    SRC = _kantart
    -> GEODB.NPL_UEUZ (writer GEODATABASE_SDE_3)
Note: GEODB.NPL_UEUZ
GEODB.NPL_UEUZ (writer GEODATABASE_SDE_3)
    attributes: BFSNR smallint, NAME char(31), REL_ID char(100), VERBINDLKT char(100), KANTART char(100), ZONENABK char(12), ZONENCODE char(12), BESCHRIEB char(80)
Note: ART
AttributeCreator_2
    ATTR_LIST = ART,Synoptische Gefahren
    -> AttributeValueMapper_4
Note: STUFE
AttributeValueMapper_4
    DIRECTION = Forward (Source To Destination)
    VAL_ATTR = STUFE
    LUT = 13,Gefahrenstufe erhebliche Gefährdung,14,Gefahrenstufe mittlere Gefährdung,15,Gefahrenstufe geringe Gefährdung,16,Gefahrenstufe Restgefährdung,17,Gefahrenhinweis
    SRC = _kantart
    -> GEODB.NPL_GEFF (writer GEODATABASE_SDE_3)
Note: GEODB.NPL_GEFF
GEODB.NPL_GEFF (writer GEODATABASE_SDE_3)
    attributes: BFSNR smallint, NAME char(31), REL_ID char(100), VERBINDLKT char(100), ART char(100), STUFE char(100), BESCHRIEB char(80)
Note: ART
AttributeValueMapper_5
    DIRECTION = Forward (Source To Destination)
    VAL_ATTR = ART
    LUT = 96,Fussweg,97,Wanderweg,98,Bergweg,99,Historischer Verkehrsweg,100,Radwanderweg,101,Veloweg,102,Uferweg,103,anderer Weg
    SRC = _kantart
    -> AttributeCreator_3
Note: NAMEWEG
AttributeCreator_3
    ATTR_LIST = NAMEWEG,@Value(BESCHRIEB)
    -> GEODB.NPL_WEWRF (writer GEODATABASE_SDE_3)
Note: GEODB.NPL_WEWRF
GEODB.NPL_WEWRF (writer GEODATABASE_SDE_3)
    attributes: BFSNR smallint, NAME char(31), REL_ID char(100), VERBINDLKT char(100), NAMEWEG char(80), ART char(100), BESCHRIEB char(80)
Note: ART
AttributeValueMapper_6
    DIRECTION = Forward (Source To Destination)
    VAL_ATTR = ART
    LUT = 0,Stehendes Gewässer,1,Fliessgewässer
    SRC = _kantart
    -> GEODB.NPL_GEGEWF (writer GEODATABASE_SDE_3)
Note: GEODB.NPL_GEGEWF
GEODB.NPL_GEGEWF (writer GEODATABASE_SDE_3)
    attributes: BFSNR smallint, NAME char(31), REL_ID char(100), VERBINDLKT char(100), ART char(100), BESCHRIEB char(80)
Note: SCHUTZGRAD
AttributeValueMapper_7
    DIRECTION = Forward (Source To Destination)
    VAL_ATTR = SCHUTZGRAD
    LUT = 1,geschützt,2,schützenswert,3,erhaltenswert,4,unbekannt,5,reduziert
    SRC = SCHUTZG
    -> AttributeValueMapper_8
Note: KANTART
AttributeValueMapper_8
    DIRECTION = Forward (Source To Destination)
    VAL_ATTR = KANTART
    LUT = 37,Landschaftsschutzgebiet,38,Landschaftsschongebiet,39,Kulturlandschaftsschutzgebiet,40,Moorlandschaft,41,Naturdenkmal,42,Aussichtspunkt,43,Aussichtslage,44,Aussichtsschutz,45,Naturschutzgebiet,46,Landschaft andere,47,Ortsbildschutzgebiet,48,Ortsbilderhaltungsgebiet,49,Strukturerhaltungsgebiet,50,Altstadtgebiet,51,Umgebungsschutzgebiet,52,Ortsbild andere,53,Einzelbaute,54,Baugruppe,55,Anhangobjekt,56,Archäologisches Schutzgebiet,57,Archäologisches Schutzobjekt,58,Geschichtliche Stätte andere,59,Kulturobjekt,60,Trockenstandort,61,Feuchtgebiet,62,Amphibienlaichgebiet,63,Wiesenstandort,64,Artenreiche Wiese,65,Hecken, Feldgehölz,66,Ufervegetation,67,Ufergehölz,68,Riedgebiet,69,seltene Waldgesellschaft,70,Trockenmauer,71,Hochstammobstgarten,72,Biotop andere,73,Hochmoor,74,Flachmoor,75,Uebergangsmoor,76,Moor anderes,77,Auen,78,Findling,79,Gletscherschliff,80,Gletschermühle,81,Geologischer Aufschluss,82,Mineralienfundstelle,83,Fundstelle Versteinerung,84,Doline,85,Geologisches Objekt anderes,86,Einzelbaum,87,Baumgruppe,88,Baumreihe Allee,89,Hochstammfeldobstbaum,90,Botanisches Objekt,91,Artenschutzzone,92,Wildschutzgebiet,93,Jagdbannbezirk,94,Vogelreservat,95,Tierschutz andere
    SRC = _kantart
    -> GEODB.NPL_NHSF (writer GEODATABASE_SDE_3)
Note: GEODB.NPL_NHSF
GEODB.NPL_NHSF (writer GEODATABASE_SDE_3)
    attributes: BFSNR smallint, NAME char(31), REL_ID char(100), VERBINDLKT char(100), KANTART char(100), SCHUTZGRAD char(100), BESCHRIEB char(80)
Note: GEODB.NUPLA_UEPT
GEODB.NUPLA_UEPT (reader GEODATABASE_SDE_1)
    attributes: geodb_oid integer, OBJECTID integer, BFSNR smallint, RVS_ID char(100), GENEHM date, INKRAFT date, BESCHRIEB char(80), QUALITAET smallint, VERBINDLKT smallint, KANTART smallint, PUNKTABK char(12), BEZ char(150), PLANBESCHR char(150), BEMERK char(80), DARST_C char(5), DATENVERW char(36), ZUSTAENDIG char(36), BUNDESART char(10), ORI float, BEDEUT smallint, SCHUTZG smallint, GEMNAME char(50)
    -> AttributeRenamer_12
AttributeRenamer_12
    ATTR_LIST = RVS_ID,REL_ID,"",VERBINDLKT,_verbindlkt,"",KANTART,_kantart,"",BESCHRIEB,_beschrieb,"",GENEHM,GENEHMDAT,"",GEMNAME,NAME,""
    -> Joiner_7
Note: VERBINDLKT joinen
Joiner_7
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeRenamer_13
AttributeRenamer_13
    ATTR_LIST = VERBINDT_BEZ_DE,VERBINDLKT,"",BEZ,BESCHRIEB,""
    -> AttributeValueMapper_14
Note: SCHUTZGRAD
AttributeValueMapper_14
    DIRECTION = Forward (Source To Destination)
    VAL_ATTR = SCHUTZGRAD
    LUT = 1,geschützt,2,schützenswert,3,erhaltenswert,4,unbekannt,5,reduziert
    SRC = SCHUTZG
    -> AttributeValueMapper_15
Note: KANTART
AttributeValueMapper_15
    DIRECTION = Forward (Source To Destination)
    VAL_ATTR = KANTART
    LUT = 37,Landschaftsschutzgebiet,38,Landschaftsschongebiet,39,Kulturlandschaftsschutzgebiet,40,Moorlandschaft,41,Naturdenkmal,42,Aussichtspunkt,43,Aussichtslage,44,Aussichtsschutz,45,Naturschutzgebiet,46,Landschaft andere,47,Ortsbildschutzgebiet,48,Ortsbilderhaltungsgebiet,49,Strukturerhaltungsgebiet,50,Altstadtgebiet,51,Umgebungsschutzgebiet,52,Ortsbild andere,53,Einzelbaute,54,Baugruppe,55,Anhangobjekt,56,Archäologisches Schutzgebiet,57,Archäologisches Schutzobjekt,58,Geschichtliche Stätte andere,59,Kulturobjekt,60,Trockenstandort,61,Feuchtgebiet,62,Amphibienlaichgebiet,63,Wiesenstandort,64,Artenreiche Wiese,65,Hecken, Feldgehölz,66,Ufervegetation,67,Ufergehölz,68,Riedgebiet,69,seltene Waldgesellschaft,70,Trockenmauer,71,Hochstammobstgarten,72,Biotop andere,73,Hochmoor,74,Flachmoor,75,Uebergangsmoor,76,Moor anderes,77,Auen,78,Findling,79,Gletscherschliff,80,Gletschermühle,81,Geologischer Aufschluss,82,Mineralienfundstelle,83,Fundstelle Versteinerung,84,Doline,85,Geologisches Objekt anderes,86,Einzelbaum,87,Baumgruppe,88,Baumreihe Allee,89,Hochstammfeldobstbaum,90,Botanisches Objekt,91,Artenschutzzone,92,Wildschutzgebiet,93,Jagdbannbezirk,94,Vogelreservat,95,Tierschutz andere
    SRC = _kantart
    -> GEODB.NPL_NHSP (writer GEODATABASE_SDE_3)
Note: GEODB.NPL_NHSP
GEODB.NPL_NHSP (writer GEODATABASE_SDE_3)
    attributes: BFSNR smallint, NAME char(31), REL_ID char(100), VERBINDLKT char(100), KANTART char(100), SCHUTZGRAD char(100), BESCHRIEB char(80)
Note: GEODB.NUPLA_GNGRUZO
GEODB.NUPLA_GNGRUZO (reader GEODATABASE_SDE_1)
    attributes: geodb_oid integer, OBJECTID integer, BFSNR smallint, RVS_ID char(100), GENEHM date, INKRAFT date, BESCHRIEB char(80), QUALITAET smallint, VERBINDLKT smallint, KANTART char(10), ZONENABK char(12), BEZ char(150), PLANBESCHR char(150), BEMERK char(80), DARST_C char(5), DATENVERW char(36), ZUSTAENDIG char(36), BUNDESART char(10), NZ float, NZ_ART smallint, GRUENFZ float, LAERMES smallint, FLMASS integer, BR_NUTZART char(80), BR_NMASS char(80), SHAPE.AREA double, SHAPE.LEN double, GEMNAME char(50)
    -> AttributeRenamer
Note: GEODB.NUPLA_GNZPPUEO
GEODB.NUPLA_GNZPPUEO (reader GEODATABASE_SDE_1)
    attributes: geodb_oid integer, OBJECTID integer, BFSNR smallint, RVS_ID char(100), GENEHM date, INKRAFT date, BESCHRIEB char(80), QUALITAET smallint, VERBINDLKT smallint, KANTART char(10), ZONENABK char(12), BEZ char(150), PLANBESCHR char(150), BEMERK char(80), DARST_C char(5), DATENVERW char(36), ZUSTAENDIG char(36), BUNDESART char(10), NZ float, NZ_ART smallint, GRUENFZ float, LAERMES smallint, FLMASS integer, BR_NUTZART char(80), BR_NMASS char(80), SHAPE.AREA double, SHAPE.LEN double, GEMNAME char(50)
    -> AttributeRenamer
AttributeRenamer
    ATTR_LIST = RVS_ID,REL_ID,"",VERBINDLKT,_verbindlkt,"",GEMNAME,NAME,""
    -> Joiner
Note: VERBINDLKT joinen
Joiner
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> Joiner_2
Note: KANTART joinen
Joiner_2
    MATCH_RULE_DISPLAY = Must Match Exactly One (1:1)
    CACHE_SIZE = 5000
    ORACLE8I_DB_REMOVE_SCHEMA_QUALIFIER = NO
    JOIN_KEYS = KANTART KANTART
    ORACLE8I_DB_USER_NAME = $(USERNAME)
    ORACLE8I_DB_SHOW_SYSTEM_TABLES = NO
    ORACLE8I_DB_SERVER_TYPE = ORACLE8i
    TABLE = GEODB.NUPLA_NPZONET
    JOINED_ATTRIBUTE_PREFIX = NPZONET
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeRenamer_2
AttributeRenamer_2
    ATTR_LIST = VERBINDT_BEZ_DE,VERBINDLKT,"",BEZ,ZONENNAME,"",NPZONET_BEZ_DE,KANTZONE,"",NZ,AZ,""
    -> PythonCaller
Note: Umlaute ersetzen
PythonCaller
    PYTHONSOURCE:
      import fmeobjects

      def processFeature(feature):
          kz = feature.getAttribute("KANTZONE")

          kz = kz.replace(u'ä', u'ae')
          kz = kz.replace(u'ö', u'oe')
          kz = kz.replace(u'ü', u'ue')
          kz = kz.replace(u'Ä', u'Ae')
          kz = kz.replace(u'Ö', u'Oe')
          kz = kz.replace(u'Ü', u'Ue')

          feature.setAttribute("KANTZONE",kz)
    PYTHONSYMBOL = processFeature
    -> StringReplacer
Note: Uebriges Gebiet ersetzen
StringReplacer
    SRC_ATTRS = KANTZONE
    REGEXP = no
    CASE = yes
    REPLACE_TEXT = uebriges Gebiet
    NO_MATCH = _FME_NO_OP_
    FIND_TEXT = Uebriges Gebiet
    -> AttributeValueMapper
Note: AZ_ART mappen
AttributeValueMapper
    DIRECTION = Forward (Source To Destination)
    VAL_ATTR = AZART
    LUT = 0,1,1,2,2,3,3,4,4,5,5,6
    SRC = NZ_ART
    -> FeatureTypeFilter
FeatureTypeFilter
    ATTRIBUTES = <BLANK>,<UNFILTERED>,GEODB.NUPLA_GNZPPUEO,GEODB.NUPLA_GNGRUZO
    GEODB.NUPLA_GNGRUZO -> GEODB.NPL_GNGZ (writer GEODATABASE_SDE_3)
    GEODB.NUPLA_GNZPPUEO -> AttributeValueMapper_19
Note: ZPP/UEO ZONENCODE / mappen (Bern only)
AttributeValueMapper_19
    DIRECTION = Forward (Source To Destination)
    VAL_ATTR = ZONENCODE
    DEFAULT_VALUE = FME_NULL_VALUE
    LUT = UEO,61,ZPP,62
    SRC = KANTART
    -> Tester
Note: Altstadtperimeter (nur Stadt Bern) / ummappen
Tester
    TEST_MODE = Automatic
    TEST_DESCRIPTION = ""
    BOOL_OP = OR
    TEST_CLAUSE = TEST @Value(ZONENNAME) BEGINS_WITH Altstadtperimeter
    FAILED -> GEODB.NPL_GNGU (writer GEODATABASE_SDE_3)
    PASSED -> AttributeCreator_5
AttributeCreator_5
    ATTR_LIST = ZONENCODE,69
    -> GEODB.NPL_GNGU (writer GEODATABASE_SDE_3)
Note: GEODB.NPL_GNGU
GEODB.NPL_GNGU (writer GEODATABASE_SDE_3)
    attributes: BFSNR smallint, NAME char(31), REL_ID char(100), VERBINDLKT char(100), ZONENABK char(12), ZONENCODE char(12), ZONENNAME char(60), KANTZONE char(100), AZ float, AZART char(40)
Note: GEODB.NPL_GNGZ
GEODB.NPL_GNGZ (writer GEODATABASE_SDE_3)
    attributes: BFSNR smallint, NAME char(31), REL_ID char(100), VERBINDLKT char(100), ZONENABK char(12), ZONENCODE char(12), ZONENNAME char(60), KANTZONE char(100), AZ float, AZART char(40)
Note: GEODB.NUPLA_UELARMES
GEODB.NUPLA_UELARMES (reader GEODATABASE_SDE_1)
    attributes: geodb_oid integer, OBJECTID integer, BFSNR smallint, RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10), SHAPE.AREA double, SHAPE.LEN double, GEMNAME char(50)
    -> AttributeRenamer_3
AttributeRenamer_3
    ATTR_LIST = RVS_ID,REL_ID,"",VERBINDLKT,_verbindlkt,"",KANTART,_kantart,"",GEMNAME,NAME,""
    -> Joiner_3
Note: VERBINDLKT joinen
Joiner_3
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeValueMapper_2
Note: KANTART mappen
AttributeValueMapper_2
    DIRECTION = Forward (Source To Destination)
    VAL_ATTR = KANTART
    LUT = 7,Lärmempfindlichkeitsstufe I,8,Lärmempfindlichkeitsstufe II,9,Lärmempfindlichkeitsstufe II aufgestuft,10,Lärmempfindlichkeitsstufe III,11,Lärmempfindlichkeitsstufe III aufgestuft,12,Lärmempfindlichkeitsstufe IV,19,ES-Planungsgebiet
    SRC = _kantart
    -> AttributeRenamer_4
AttributeRenamer_4
    ATTR_LIST = VERBINDT_BEZ_DE,VERBINDLKT,""
    -> GEODB.NPL_UELAERM (writer GEODATABASE_SDE_3)
Note: GEODB.NPL_UELAERM
GEODB.NPL_UELAERM (writer GEODATABASE_SDE_3)
    attributes: BFSNR smallint, NAME char(31), REL_ID char(100), VERBINDLKT char(100), KANTART char(100), ZONENABK char(12), ZONENCODE char(12)
Note: GEODB.NUPLA_RVST
GEODB.NUPLA_RVST (reader GEODATABASE_SDE_2)
    attributes: geodb_oid integer, OBJECTID integer, BFSNR smallint, GEMNAME char(50), RVS_ID char(100), ART char(40), TITEL char(200), OFFIZTITEL char(200), ABKUERZUNG char(20), OFFIZNR char(20), DOKUMENT char(100), ARTIKELNR char(40), ORDNNR smallint, ZUSTAENDIG char(36)
    -> AttributeRenamer_7
AttributeRenamer_7
    ATTR_LIST = RVS_ID,RELID,"",DOKUMENT,TEXTIMWEB,"",GEMNAME,NAME,""
    -> GEODB.NPL_RVT (writer GEODATABASE_SDE_3)
Note: GEODB.NPL_RVT
GEODB.NPL_RVT (writer GEODATABASE_SDE_3)
    attributes: BFSNR smallint, NAME char(31), RELID char(100), ARTIKELNR char(40), ART char(50), TEXTIMWEB char(200), TITEL char(200), OFFIZTITEL char(200), ABKUERZUNG char(10), OFFIZNR char(20)
Note: GEODB.NUPLA_UELN
GEODB.NUPLA_UELN (reader GEODATABASE_SDE_1)
    attributes: geodb_oid integer, OBJECTID integer, BFSNR smallint, RVS_ID char(100), GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, ABSTLINKS float, ABSTRECHTS float, ABSTDEF smallint, STATUS smallint, SHAPE.LEN double,
      GEMNAME char(50)
    -> AttributeRenamer_10
AttributeRenamer_10
    ATTR_LIST = RVS_ID,REL_ID,"",VERBINDLKT,_verbindlkt,"",KANTART,_kantart,"",BESCHRIEB,_beschrieb,"",GENEHM,GENEHMDAT,"",GEMNAME,NAME,""
    -> Joiner_6
Note: VERBINDLKT joinen
Joiner_6
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeRenamer_11
AttributeRenamer_11
    ATTR_LIST = VERBINDT_BEZ_DE,VERBINDLKT,"",BEZ,BESCHRIEB,""
    -> TestFilter_2
Note: Aufteilung in Featureclasses
TestFilter_2
    TEST_LIST = BOOL_OP,OR,COMPOSITE_TEST,<Unused>,TEST_CLAUSE,"TEST @Value(_kantart) IN 23-36",UEUL,BOOL_OP,OR,COMPOSITE_TEST,<Unused>,TEST_CLAUSE,"TEST @Value(_kantart) IN 96-103",WEWRL,BOOL_OP,OR,COMPOSITE_TEST,<Unused>,TEST_CLAUSE,"TEST @Value(_kantart) IN 0,1",GEGEWL,BOOL_OP,OR,COMPOSITE_TEST,<Unused>,TEST_CLAUSE,"TEST @Value(_kantart) IN 37-95",NHSL
    DEFAULT_VALUE = <UNFILTERED>
    UEUL -> AttributeValueMapper_9
    WEWRL -> AttributeValueMapper_10
    GEGEWL -> AttributeValueMapper_11
    NHSL -> AttributeValueMapper_12
Note: KANTART
AttributeValueMapper_9
    DIRECTION = Forward (Source To Destination)
    VAL_ATTR = KANTART
    LUT = 23,Abstandslinie Eisenbahn,24,Abstandslinie Nationalstrasse,25,Abstandslinie Strasse,26,Abstandslinie Leitung,27,Gewässerabstandslinie,28,Wald-Baulinie,29,Baulinie,30,Garagebaulinie,31,Erdgeschossbaulinie,32,Gestaltungsbaulinie,33,Rückwärtige Baulinie,34,Innenbaulinie,35,Hilfsbaulinie,36,weitere Baulinie
    SRC = _kantart
    -> TestFilter_3
Note: UEPROJ rausfiltern
TestFilter_3
    TEST_LIST = BOOL_OP,OR,COMPOSITE_TEST,<Unused>,TEST_CLAUSE,"TEST @Value(STATUS) = 3",UEPROJ
    DEFAULT_VALUE = UEUL
    UEUL -> GEODB.NPL_UEUL (writer GEODATABASE_SDE_3)
    UEPROJ -> GEODB.NPL_UEPROJ (writer GEODATABASE_SDE_3)
Note: GEODB.NPL_UEPROJ
GEODB.NPL_UEPROJ (writer GEODATABASE_SDE_3)
    attributes: BFSNR smallint, NAME char(31), REL_ID char(100), VERBINDLKT char(100), KANTART char(100), LINIENABK char(12), LINIENCODE char(12), BESCHRIEB char(80), GENEHMDAT date, PLANBESCHR char(30)
Note: GEODB.NPL_UEUL
GEODB.NPL_UEUL (writer GEODATABASE_SDE_3)
    attributes: BFSNR smallint, NAME char(31), REL_ID char(100), VERBINDLKT char(100), KANTART char(100), LINIENABK char(12), LINIENCODE char(12), BESCHRIEB char(80), GENEHMDAT date, PLANBESCHR char(30)
Note: ART
AttributeValueMapper_10
    DIRECTION = Forward (Source To Destination)
    VAL_ATTR = ART
    LUT = 96,Fussweg,97,Wanderweg,98,Bergweg,99,Historischer Verkehrsweg,100,Radwanderweg,101,Veloweg,102,Uferweg,103,anderer Weg
    SRC = _kantart
    -> AttributeCreator_4
Note: NAMEWEG
AttributeCreator_4
    ATTR_LIST = NAMEWEG,@Value(BESCHRIEB)
    -> GEODB.NPL_WEWRL (writer GEODATABASE_SDE_3)
Note: GEODB.NPL_WEWRL
GEODB.NPL_WEWRL (writer GEODATABASE_SDE_3)
    attributes: BFSNR smallint, NAME char(31), REL_ID char(100), VERBINDLKT char(100), NAMEWEG char(80), ART char(100), BESCHRIEB char(80)
Note: ART
AttributeValueMapper_11
    DIRECTION = Forward (Source To Destination)
    VAL_ATTR = ART
    LUT = 0,Stehendes Gewässer,1,Fliessgewässer
    SRC = _kantart
    -> GEODB.NPL_GEGEWL (writer GEODATABASE_SDE_3)
Note: GEODB.NPL_GEGEWL
GEODB.NPL_GEGEWL (writer GEODATABASE_SDE_3)
    attributes: BFSNR smallint, NAME char(31), REL_ID char(100), VERBINDLKT char(100), ART char(100), BESCHRIEB char(80)
Note: SCHUTZGRAD
AttributeValueMapper_12
    DIRECTION = Forward (Source To Destination)
    VAL_ATTR = SCHUTZGRAD
    LUT = 1,geschützt,2,schützenswert,3,erhaltenswert,4,unbekannt,5,reduziert
    SRC = SCHUTZG
    -> AttributeValueMapper_13
Note: KANTART
AttributeValueMapper_13
    DIRECTION = Forward (Source To Destination)
    VAL_ATTR = KANTART
    LUT = 37,Landschaftsschutzgebiet,38,Landschaftsschongebiet,39,Kulturlandschaftsschutzgebiet,40,Moorlandschaft,41,Naturdenkmal,42,Aussichtspunkt,43,Aussichtslage,44,Aussichtsschutz,45,Naturschutzgebiet,46,Landschaft andere,47,Ortsbildschutzgebiet,48,Ortsbilderhaltungsgebiet,49,Strukturerhaltungsgebiet,50,Altstadtgebiet,51,Umgebungsschutzgebiet,52,Ortsbild andere,53,Einzelbaute,54,Baugruppe,55,Anhangobjekt,56,Archäologisches Schutzgebiet,57,Archäologisches Schutzobjekt,58,Geschichtliche Stätte andere,59,Kulturobjekt,60,Trockenstandort,61,Feuchtgebiet,62,Amphibienlaichgebiet,63,Wiesenstandort,64,Artenreiche Wiese,65,Hecken, Feldgehölz,66,Ufervegetation,67,Ufergehölz,68,Riedgebiet,69,seltene Waldgesellschaft,70,Trockenmauer,71,Hochstammobstgarten,72,Biotop andere,73,Hochmoor,74,Flachmoor,75,Uebergangsmoor,76,Moor anderes,77,Auen,78,Findling,79,Gletscherschliff,80,Gletschermühle,81,Geologischer Aufschluss,82,Mineralienfundstelle,83,Fundstelle Versteinerung,84,Doline,85,Geologisches Objekt anderes,86,Einzelbaum,87,Baumgruppe,88,Baumreihe Allee,89,Hochstammfeldobstbaum,90,Botanisches Objekt,91,Artenschutzzone,92,Wildschutzgebiet,93,Jagdbannbezirk,94,Vogelreservat,95,Tierschutz andere
    SRC = _kantart
    -> GEODB.NPL_NHSL (writer GEODATABASE_SDE_3)
Note: GEODB.NPL_NHSL
GEODB.NPL_NHSL (writer GEODATABASE_SDE_3)
    attributes: BFSNR smallint, NAME char(31), REL_ID char(100), VERBINDLKT char(100), KANTART char(100), SCHUTZGRAD char(100), BESCHRIEB char(80)
Note: GEODB.NUPLA_ABGRZ
GEODB.NUPLA_ABGRZ (reader GEODATABASE_SDE_2)
    attributes: geodb_oid integer, OBJECTID integer, BFSNR smallint, GEMNAME char(50), ART char(30), DARST_C char(5), SHAPE.LEN double
    -> GEODB.NPL_ABGRENZ (writer GEODATABASE_SDE_3)
Note: GEODB.NPL_ABGRENZ
GEODB.NPL_ABGRENZ (writer GEODATABASE_SDE_3)
    attributes: BFSNR smallint, NAME char(31), ART char(30)
Note: GEODB.NUPLA_GNBAUWS
GEODB.NUPLA_GNBAUWS (reader GEODATABASE_SDE_2)
    attributes: geodb_oid integer, OBJECTID integer, BFSNR smallint, GEMNAME char(50), RVS_ID char(100), GENEHM date, INKRAFT date, BWTYP smallint, QUALITAET smallint, GEBL float, GEBLU smallint, GEBT float, GEBTU smallint, GEBLSYM char(2), GEBTSYM char(2), DARST_C char(5), DATENVERW char(36), ZUSTAENDIG char(36), SHAPE.AREA double, SHAPE.LEN double
    -> AttributeValueMapper_16
Note: GEBLANGUNB
AttributeValueMapper_16
    DIRECTION = Forward (Source To Destination)
    VAL_ATTR = GEBLANGUNB
    DEFAULT_VALUE = FME_NULL_VALUE
    LUT = 1,unbeschränkt
    SRC = GEBLU
    -> AttributeValueMapper_17
Note: GEBTIEFUNB
AttributeValueMapper_17
    DIRECTION = Forward (Source To Destination)
    VAL_ATTR = GEBTIEFUNB
    DEFAULT_VALUE = FME_NULL_VALUE
    LUT = 1,unbeschränkt
    SRC = GEBTU
    -> AttributeValueMapper_18
Note: BAUWEISTYP
AttributeValueMapper_18
    DIRECTION = Forward (Source To Destination)
    VAL_ATTR = BAUWEISTYP
    LUT = 1,unbekannt,2,geschlossen,3,offen
    SRC = BWTYP
    -> GEODB.NPL_GNBAUW (writer GEODATABASE_SDE_3)
Note: GEODB.NPL_GNBAUW
GEODB.NPL_GNBAUW (writer GEODATABASE_SDE_3)
    attributes: BFSNR smallint, NAME char(31), REL_ID char(100), GEBLAENGE smallint, GEBLANGUNB char(20), GEBLANGSYM char(2), GEBTIEFE smallint, GEBTIEFUNB char(20), GEBTIEFSYM char(2), BAUWEISTYP char(100)
Note: GEODB.NUPLA_GNNUTZBK
GEODB.NUPLA_GNNUTZBK (reader GEODATABASE_SDE_1)
    attributes: geodb_oid integer, OBJECTID integer, BFSNR smallint, GEMNAME char(50), RVS_ID char(100), GENEHM date, INKRAFT date, BESCHRIEB char(80), QUALITAET smallint, VERBINDLKT smallint, KANTART char(10), ZONENABK char(12), BEZ char(150), PLANBESCHR char(150), BEMERK char(80), DARST_C_NZ char(5), DATENVERW char(36), ZUSTAENDIG char(36), BUNDESART char(10), NZ float, NZ_ART smallint, GRUENFZ float, LAERMES smallint, FLMASS integer, BR_NUTZART char(80), BR_NMASS char(80), NZ_TYP char(100), BK_TYP char(100), DARST_C_BK char(5), SHAPE.AREA double,
      SHAPE.LEN double
    -> AttributeRenamer_15
AttributeRenamer_15
    ATTR_LIST = VERBINDLKT,_verbindlkt,""
    -> Joiner_8
Note: VERBINDLKT joinen
Joiner_8
    MATCH_RULE_DISPLAY = Must Match Exactly One (1:1)
    CACHE_SIZE = 5000
    ORACLE8I_DB_REMOVE_SCHEMA_QUALIFIER = NO
    JOIN_KEYS = _verbindlkt VERBINDLKT
    ORACLE8I_DB_USER_NAME = $(USERNAME)
    ORACLE8I_DB_SHOW_SYSTEM_TABLES = NO
    ORACLE8I_DB_SERVER_TYPE = ORACLE8i
    TABLE = GEODB.NUPLA_VERBINDT
    JOINED_ATTRIBUTE_PREFIX = VERBINDT
    DATASET = $(DATABASE)
    ORACLE8I_DB_PASSWORD = $(PASSWORD)
    ADDED_FIELDS = BEZ_DE
    PREFETCH_EXHAUSTIVE = Yes
    ORACLE8I_DB_PERSISTENT_CONNECTION = YES
    FORMAT = ORACLE8I_DB
    JOINED -> AttributeRenamer_16
AttributeRenamer_16
    ATTR_LIST = VERBINDT_BEZ_DE,VERBINDLKT,""
    -> GEODB.NPL_GNNUTZZO (writer GEODATABASE_SDE_3)
Note: GEODB.NPL_GNNUTZZO
GEODB.NPL_GNNUTZZO (writer GEODATABASE_SDE_3)
    attributes: BFSNR smallint, NAME char(31), REL_ID char(100), VERBINDLKT char(100), ZONENABK char(12), ZONENCODE char(12), ZONENNAME char(60), KANTZONE char(100), AZ float, AZART char(40), NZTYP char(100), BKTYP char(100)
GEODB.NPL_WAABPER (writer GEODATABASE_SDE_3) [off]
    attributes: geodb_oid integer, OBJECTID integer, BFSNR smallint, NAME char(31), REL_ID char(100), SHAPE.AREA double, SHAPE.LEN double
