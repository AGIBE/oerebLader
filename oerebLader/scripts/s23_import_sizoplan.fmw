FME workspace s23_import_sizoplan.fmw
Startup Python:
      # -*- coding: utf-8 -*-
      import fmeobjects

      #=======================================================================================
      # Mehrsprachige Felder in INTERLIS2 behandeln
      def processMultilangFields(feature):

          multilangFields = feature.getAttribute('multilangfields').split(",")

          for mlField in multilangFields:
              content_de = ""
              content_fr = ""
              content_it = ""

              att_Language_list = feature.getAttribute(mlField + '{0}.LocalisedText{}.Language')
              att_Text_list = feature.getAttribute(mlField + '{0}.LocalisedText{}.Text')

              # wenn das Multilang-Feld nicht abgefüllt ist, soll es nicht bearbeitet werden
              if att_Language_list is not None:

                      for i in range(len(att_Language_list)):
                          if att_Language_list[i]=="de":
                              content_de = att_Text_list[i]
                          if att_Language_list[i]=="fr":
                              content_fr = att_Text_list[i]
                          if att_Language_list[i]=="it":
                              content_it = att_Text_list[i]

                      # Wenn der Text nur in einer Sprache vorhanden ist, wird er auch für die andere Sprache verwendet
                      if content_de == "":
                          content_de = content_fr
                      if content_de == "":
                          content_de = content_it
                      if content_fr == "":
                          content_fr = content_de
                      if content_fr == "":
                          content_fr = content_it

              feature.setAttribute(mlField + "_DE", content_de)
              feature.setAttribute(mlField + "_FR", content_fr)

Parameters:
- XTF_FILE =   # XTF-File
- USERNAME =   # Username
- PASSWORD =   # PASSWORD Password
- DATABASE =   # Database
- MODELLABLAGE =   # Modellablage
- LOGFILE =   # Logfile
- GEODB_PG_DATABASE =
- GEODB_PG_USERNAME =
- GEODB_PG_PASSWORD =
- GEODB_PG_HOST =
- GEODB_PG_PORT =

Readers:
- ch.ehi.fme.Main_3: ch.ehi.fme.Main from $(XTF_FILE)

Writers:
- GEODATABASE_SDE_1: GEODATABASE_SDE to sde
- POSTGIS_1: POSTGIS to $(GEODB_PG_DATABASE) in EPSG:2056

Note: SafetyZones_WithLatestModification.Geometry
SafetyZonePlan_LV95_V1_2.SafetyZones_WithLatestModification.Geometry (reader ch.ehi.fme.Main_3)
    attributes: xtf_id xtf_char(200), Type{}.xtf_class xtf_char(84), Type{}.Reference xtf_char(200), Modification{}.xtf_class xtf_char(84), Modification{}.ValidFrom xtf_datetime, Modification{}.ValidUntil xtf_datetime, Modification{}.LatestModification xtf_datetime, Modification{}.Modifications{}.xtf_class xtf_char(84), Modification{}.Modifications{}.Reference xtf_char(200), Zone xtf_char(200)
    -> AttributeValueMapper
Note: Zonentyp extrahieren und mappen
AttributeValueMapper
    DIRECTION = Forward (Source To Destination)
    LUT = 108-T-01,1,108-T-02,2,108-T-03,3,108-T-04,4,108-T-05,5
    SRC = Type{0}.Reference
    VAL_ATTR = ZONENTYP
    -> AttributeRemover_2
AttributeRemover_2
    LIST_ATTRS = Modification{}.LatestModification Modification{}.Modifications{} Type{}.Reference Modification{} Modification{}.Modifications{}.Reference Type{}.Ref Modification{}.ValidFrom Modification{}.ValidUntil Type{}.xtf_class Modification{}.xtf_class Modification{}.Modifications{}.xtf_class Type{}
    REMOVE_ATTRS = xtf_id,type_xtf_class,type_Reference,type_Ref
    -> FeatureMerger_3 [REQUESTOR]
Note: SafetyZones_WithLatestModification.SafetyZone
SafetyZonePlan_LV95_V1_2.SafetyZones_WithLatestModification.SafetyZone (reader ch.ehi.fme.Main_3)
    attributes: xtf_id xtf_char(200), Identifier xtf_char(30), Name{}.xtf_class xtf_char(84), Name{}.LocalisedText{}.xtf_class xtf_char(84), Name{}.LocalisedText{}.Language xtf_char(255), Name{}.LocalisedText{}.Text xtf_buffer, Status{}.xtf_class xtf_char(84), Status{}.Reference xtf_char(200), Originator xtf_buffer, Canton xtf_char(255), Municipality xtf_buffer, ApprovalDate xtf_datetime, Validity{}.xtf_class xtf_char(84), Validity{}.ValidFrom xtf_datetime, Validity{}.ValidUntil xtf_datetime, Validity{}.LatestModification xtf_datetime, Validity{}.Modifications{}.xtf_class xtf_char(84), Validity{}.Modifications{}.Reference xtf_char(200), Description{}.xtf_class xtf_char(84), Description{}.LocalisedText{}.xtf_class xtf_char(84), Description{}.LocalisedText{}.Language xtf_char(255), Description{}.LocalisedText{}.Text xtf_buffer
    -> AttributeCreator
Note: STATUS extrahieren
AttributeValueMapper_2
    DIRECTION = Forward (Source To Destination)
    LUT = 108-S-01,1,108-S-02,2
    SRC = Status{0}.Reference
    VAL_ATTR = STATUS
    -> PythonCaller_3
Note: Datum formatieren
PythonCaller_3
    NEW_ATTRIBUTES = GENEHMIGT
    PYTHONSOURCE:
      import fmeobjects
      import datetime
      # Template Function interface:
      def processDatetime(feature):
          date = feature.getAttribute("ApprovalDate")
          date_obj = datetime.datetime.strptime(date, "%Y-%m-%dT%H:%M:%S.%f")
          formatted_date = date_obj.strftime("%d.%m.%Y")

          feature.setAttribute("GENEHMIGT", formatted_date)
    PYTHONSYMBOL = processDatetime
    -> AttributeRemover
AttributeRemover
    LIST_ATTRS = Name{} Description{}.LocalisedText{}.xtf_class Validity{}.Modifications{}.xtf_class Name{}.LocalisedText{} Validity{}.Modifications{}.Reference Name{}.LocalisedText{}.Text Name{}.LocalisedText{}.xtf_class Description{} Name{}.xtf_class Validity{}.LatestModification Description{}.LocalisedText{}.Text Validity{} Description{}.LocalisedText{} Validity{}.ValidUntil Name{}.LocalisedText{}.Language Validity{}.ValidFrom Validity{}.Modifications{} Description{}.xtf_class Status{}.Reference Validity{}.xtf_class Description{}.LocalisedText{}.Language Status{} Status{}.xtf_class Status{}.Ref
    REMOVE_ATTRS = ApprovalDate,multilangfields,status_xtf_class,status_Reference,status_Ref
    -> AttributeRenamer_2
AttributeRenamer_2
    ATTR_LIST = Name_DE,NAME,"",Name_FR,NAME_F,"",Description_DE,BESCHR_D,"",Description_FR,BESCHR_F,"",Canton,KANTON,"",Municipality,GEMEINDE,"",Originator,ORIGINATOR,"",Identifier,ZONENID,""
    -> FeatureMerger_3 [SUPPLIER]
    -> AttributeRemover_6
FeatureMerger_3
    IGNORE_NULLS = Yes
    JOIN_KEYS = @Value(Zone) @Value(xtf_id) AUTO
    MERGE_TYPE = Attributes Only
    PROCESS_DUPS = No
    SUPPLIERS_FIRST = No
    SUPPLIER_PREFIX_DUMMY = YES
    MERGED -> Sorter
Sorter
    SORT_PARM = ZONENID ALPHA ASCENDING
    SORTED -> AttributeRemover_11
AttributeRemover_11
    REMOVE_ATTRS = Zone,xtf_id,NAME_F
    -> BulkAttributeRenamer
    -> SIZOPLAN_SIZOPLAN (writer GEODATABASE_SDE_1)
Note: GEODB.SIZOPLAN_SIZOPLAN
SIZOPLAN_SIZOPLAN (writer GEODATABASE_SDE_1)
    attributes: ZONENID char(30), ZONENTYP smallint, ORIGINATOR char(255), KANTON char(2), GEMEINDE char(1024), NAME char(255), STATUS smallint, GENEHMIGT char(10), BESCHR_D char(1024), BESCHR_F char(1024)
BulkAttributeRenamer
    ATTRCHOICE = All Attributes
    CASE_CHANGE_TYPE = lower
    MODE_CHOICE = RENAME
    PATTERN_ACTION_DISP = CASECHANGE
    -> sizoplan_sizoplan (writer POSTGIS_1)
Note: geodb.sizoplan_sizoplan
sizoplan_sizoplan (writer POSTGIS_1)
    attributes: zonenid varchar(30), zonentyp int2, originator varchar(255), kanton varchar(2), gemeinde varchar(1024), name varchar(255), status int2, genehmigt varchar(10), beschr_d varchar(1024), beschr_f varchar(1024)
AttributeRemover_6
    REMOVE_ATTRS = ORIGINATOR,KANTON,GEMEINDE,NAME,NAME_F,BESCHR_D,BESCHR_F,STATUS,GENEHMIGT
    -> FeatureMerger_5 [REQUESTOR]
Note: RelatedDocuments_WithLatestModification.RegulationDocument
SafetyZonePlan_LV95_V1_2.RelatedDocuments_WithLatestModification.RegulationDocument (reader ch.ehi.fme.Main_3)
    attributes: xtf_id xtf_char(200), Title xtf_buffer, Weblink xtf_char(1023), Language xtf_char(255), Modification{}.xtf_class xtf_char(84), Modification{}.ValidFrom xtf_datetime, Modification{}.ValidUntil xtf_datetime, Modification{}.LatestModification xtf_datetime, Modification{}.Modifications{}.xtf_class xtf_char(84), Modification{}.Modifications{}.Reference xtf_char(200), Description{}.xtf_class xtf_char(84), Description{}.LocalisedText{}.xtf_class xtf_char(84), Description{}.LocalisedText{}.Language xtf_char(255), Description{}.LocalisedText{}.Text xtf_buffer
    -> AttributeCreator_4
AttributeRemover_5
    LIST_ATTRS = Description{}.LocalisedText{} Modification{}.LatestModification Modification{}.Modifications{} Modification{} Modification{}.Modifications{}.Reference Description{} Description{}.LocalisedText{}.Language Modification{}.ValidFrom Description{}.LocalisedText{}.Text Description{}.xtf_class Modification{}.ValidUntil Modification{}.xtf_class Modification{}.Modifications{}.xtf_class Description{}.LocalisedText{}.xtf_class
    REMOVE_ATTRS = Language,multilangfields,Description_FR
    -> AttributeRenamer_4
AttributeRenamer_4
    ATTR_LIST = Title,TITEL,"",Weblink,WEBLINK,"",Description_DE,BESCHRIEB,"",xtf_id,doku_xtf_id,""
    -> FeatureMerger_4 [SUPPLIER]
Note: RelatedDocuments_WithLatestModification.Document
SafetyZonePlan_LV95_V1_2.RelatedDocuments_WithLatestModification.Document (reader ch.ehi.fme.Main_3)
    attributes: xtf_id xtf_char(200), Title xtf_buffer, Weblink xtf_char(1023), Language xtf_char(255), Modification{}.xtf_class xtf_char(84), Modification{}.ValidFrom xtf_datetime, Modification{}.ValidUntil xtf_datetime, Modification{}.LatestModification xtf_datetime, Modification{}.Modifications{}.xtf_class xtf_char(84), Modification{}.Modifications{}.Reference xtf_char(200), Description{}.xtf_class xtf_char(84), Description{}.LocalisedText{}.xtf_class xtf_char(84), Description{}.LocalisedText{}.Language xtf_char(255), Description{}.LocalisedText{}.Text xtf_buffer
    -> AttributeCreator_3
AttributeRemover_3
    LIST_ATTRS = Description{}.LocalisedText{} Modification{}.LatestModification Modification{}.Modifications{} Modification{} Modification{}.Modifications{}.Reference Description{} Description{}.LocalisedText{}.Language Modification{}.ValidFrom Description{}.LocalisedText{}.Text Description{}.xtf_class Modification{}.ValidUntil Modification{}.xtf_class Modification{}.Modifications{}.xtf_class Description{}.LocalisedText{}.xtf_class
    REMOVE_ATTRS = Language,multilangfields,Description_FR
    -> AttributeRenamer_3
AttributeRenamer_3
    ATTR_LIST = Title,TITEL,"",Weblink,WEBLINK,"",Description_DE,BESCHRIEB,"",xtf_id,doku_xtf_id,""
    -> FeatureMerger [SUPPLIER]
Note: SafetyZones_WithLatestModification.SafetyZonePrescription
SafetyZonePlan_LV95_V1_2.SafetyZones_WithLatestModification.SafetyZonePrescription (reader ch.ehi.fme.Main_3)
    attributes: xtf_id xtf_char(200), Prescription xtf_char(200), Restriction xtf_char(200)
    -> AttributeRemover_7
AttributeRemover_7
    REMOVE_ATTRS = xtf_id
    -> FeatureMerger_4 [REQUESTOR]
FeatureMerger_4
    IGNORE_NULLS = Yes
    JOIN_KEYS = @Value(Prescription) @Value(doku_xtf_id) AUTO
    MERGE_TYPE = Attributes Only
    PROCESS_DUPS = No
    SUPPLIERS_FIRST = No
    SUPPLIER_PREFIX_DUMMY = YES
    MERGED -> FeatureMerger_5 [SUPPLIER]
FeatureMerger_5
    GEOM_TYPE = Build Polygons
    IGNORE_NULLS = Yes
    JOIN_KEYS = @Value(xtf_id) @Value(Restriction) AUTO
    LIST_NAME = regulations
    MERGE_TYPE = Attributes Only
    PROCESS_DUPS = Yes
    SUPPLIERS_FIRST = No
    SUPPLIER_PREFIX_DUMMY = YES
    MERGED -> AttributeRemover_4
AttributeRemover_4
    REMOVE_ATTRS = TITEL,WEBLINK,BESCHRIEB
    -> ListExploder
ListExploder
    INDEX_ATTR = _element_index
    LIST_ATTR = regulations{}
    MODE = List Elements and Original Attributes
    LIST_FOUND -> AttributeRemover_10
    LIST_FOUND -> AttributeRemover_9
AttributeRemover_10
    REMOVE_ATTRS = xtf_id,Prescription,_element_index,Restriction,doku_xtf_id
    -> Sorter_3
    -> BulkAttributeRenamer_2
AttributeRemover_9
    REMOVE_ATTRS = BESCHRIEB,xtf_id,Prescription,_element_index,WEBLINK,Restriction,TITEL
    -> FeatureMerger_2 [SUPPLIER]
Note: RelatedDocuments_WithLatestModification.OriginReference
SafetyZonePlan_LV95_V1_2.RelatedDocuments_WithLatestModification.OriginReference (reader ch.ehi.fme.Main_3)
    attributes: xtf_id xtf_char(200), Origin xtf_char(200), Reference xtf_char(200)
    -> AttributeRemover_8
AttributeRemover_8
    REMOVE_ATTRS = xtf_id
    -> FeatureMerger [REQUESTOR]
FeatureMerger
    ATTR_ACCUM_MODE = Merge Supplier
    ATTR_CONFLICT_RES = Use Requestor
    IGNORE_NULLS = No
    JOIN_KEYS = @Value(Reference) @Value(doku_xtf_id) AUTO
    MERGE_TYPE = Attributes Only
    PROCESS_DUPS = NO
    REJECT_NULL_MISSING_KEYS = No
    SUPPLIERS_FIRST = No
    MERGED -> FeatureMerger_2 [REQUESTOR]
FeatureMerger_2
    ATTR_ACCUM_MODE = Merge Supplier
    ATTR_CONFLICT_RES = Use Requestor
    IGNORE_NULLS = No
    JOIN_KEYS = @Value(Origin) @Value(doku_xtf_id) AUTO
    MERGE_TYPE = Attributes Only
    PROCESS_DUPS = NO
    REJECT_NULL_MISSING_KEYS = No
    SUPPLIERS_FIRST = No
    MERGED -> AttributeRemover_12
AttributeRemover_12
    REMOVE_ATTRS = Reference,doku_xtf_id,Origin
    -> BulkAttributeRenamer_2
    -> Sorter_3
BulkAttributeRenamer_2
    ATTRCHOICE = All Attributes
    CASE_CHANGE_TYPE = lower
    MODE_CHOICE = RENAME
    PATTERN_ACTION_DISP = CASECHANGE
    -> Sorter_2
Sorter_2
    SORT_PARM = zonenid ALPHA ASCENDING
    SORTED -> sizoplan_revo (writer POSTGIS_1)
Note: geodb.sizoplan_revo
sizoplan_revo (writer POSTGIS_1)
    attributes: zonenid varchar(30), titel varchar(255), weblink varchar(1024), beschrieb varchar(1024)
Sorter_3
    SORT_PARM = ZONENID ALPHA ASCENDING
    SORTED -> SIZOPLAN_REVO (writer GEODATABASE_SDE_1)
Note: GEODB.SIZOPLAN_REVO
SIZOPLAN_REVO (writer GEODATABASE_SDE_1)
    attributes: ZONENID char(30), TITEL char(255), WEBLINK char(1024), BESCHRIEB char(1024)

Bookmark: Mehrsprachige Felder bearbeiten
AttributeCreator
    ATTR_LIST = multilangfields,Name
    -> PythonCaller
PythonCaller
    NEW_ATTRIBUTES = Name_DE Name_FR
    PYTHONSYMBOL = processMultilangFields
    -> AttributeCreator_2
AttributeCreator_2
    ATTR_LIST = multilangfields,Description
    -> PythonCaller_2
PythonCaller_2
    NEW_ATTRIBUTES = Description_DE Description_FR
    PYTHONSYMBOL = processMultilangFields
    -> AttributeValueMapper_2

Bookmark: Mehrsprachige Felder bearbeiten
AttributeCreator_4
    ATTR_LIST = multilangfields,Description
    -> PythonCaller_4
PythonCaller_4
    NEW_ATTRIBUTES = Description_DE Description_FR
    PYTHONSYMBOL = processMultilangFields
    -> AttributeRemover_5

Bookmark: Mehrsprachige Felder bearbeiten
AttributeCreator_3
    ATTR_LIST = multilangfields,Description
    -> PythonCaller_5
PythonCaller_5
    NEW_ATTRIBUTES = Description_DE Description_FR
    PYTHONSYMBOL = processMultilangFields
    -> AttributeRemover_3
