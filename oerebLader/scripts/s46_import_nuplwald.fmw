FME workspace s46_import_nuplwald.fmw

Parameters:
- ITF_FILE =   # Interlis-Datei
- BFSNR =   # BFS-Nummer
- GEMNAME =   # Gemeindename
- OEREB2_DATABASE =   # Oereb-Database
- LIEFEREINHEIT =   # Liefereinheit
- LEGEND_BASEURL =   # Legenden-Basis-URL
- MODELLABLAGE =   # Modellablage
- OEREB2_USERNAME =   # Oereb-Username
- OEREB2_PASSWORD =   # Oereb-Passwort
- LOGFILE =   # Logfile
- GEODB_USERNAME =   # GeoDB-Username
- GEODB_DATABASE =   # GeoDB-Database
- GEODB_PASSWORD =   # GeoDB-Passwort
- INPUT_RV_DIR =   # Input-Verzeichnis RV
- OUTPUT_RV_DIR =   # Output-Verzeichnis RV
- OUTPUT_RV_URL =   # Output-URL RV
- GEODB_PG_DATABASE =
- GEODB_PG_USERNAME =
- GEODB_PG_PASSWORD =
- GEODB_PG_HOST =
- GEODB_PG_PORT =
- OEREB_PG_DATABASE =
- OEREB_PG_HOST =
- OEREB_PG_PASSWORD =
- OEREB_PG_PORT =
- OEREB_PG_USERNAME =
- STROKER =
- WALDGRENZEN_VERFUEGUNG_DE =
- WALDGRENZEN_VERFUEGUNG_FR =
- AMT_OID =
- AMT_OID_BASE =
- EXCEL_AMT =
- DAR_OID = GEODB.NPLWALD_WAFW   # DAR-OID
- RES_ID = 1
- STH_ID = 160
- law_status = inForce
- schema = forest_perimeters
- topic = ForestPerimeters

Readers:
- ch.ehi.fme.Main_1: ch.ehi.fme.Main from $(ITF_FILE) in EPSG:2056
- XLSXR_1: XLSXR from $(EXCEL_AMT)

Writers:
- ORACLE8I_DB_1: ORACLE8I_DB to $(OEREB2_DATABASE)
- GEODATABASE_SDE_1: GEODATABASE_SDE to sde
- GEODATABASE_SDE_2: GEODATABASE_SDE to sde
- FILECOPY_1: FILECOPY to C:\Windows\Temp
- POSTGIS_1: POSTGIS to $(GEODB_PG_DATABASE) in EPSG:2056
- POSTGRES_7: POSTGRES to $(OEREB_PG_DATABASE)
- POSTGRES_1: POSTGRES to $(OEREB_PG_DATABASE)
- POSTGRES_2: POSTGRES to $(OEREB_PG_DATABASE)
- POSTGIS_2: POSTGIS to $(OEREB_PG_DATABASE)
- POSTGRES_3: POSTGRES to $(OEREB_PG_DATABASE)
- POSTGRES_4: POSTGRES to $(OEREB_PG_DATABASE)
- POSTGRES_5: POSTGRES to $(OEREB_PG_DATABASE)
- POSTGRES_6: POSTGRES to $(OEREB_PG_DATABASE)

Note: WF_LinienelementWald
DM16NplBE.Nutzungsplanung.WF_LinienelementWald (reader ch.ehi.fme.Main_1)
    attributes: xtf_id xtf_char(200), Objekt xtf_char(200), Genehmigung xtf_date, Inkraftsetzung xtf_date, Qualitaet xtf_char(255)
    -> UUIDGenerator
Note: LIN_OID
UUIDGenerator
    UUID_ATTR = LIN_OID
    -> FeatureMerger [REQUESTOR]
Note: WF_FeststellungWald
DM16NplBE.Nutzungsplanung.WF_FeststellungWald (reader ch.ehi.fme.Main_1)
    attributes: xtf_id xtf_char(200), Verbindlichkeit xtf_char(255), Bemerkung xtf_char(80), Datenverwaltungsstelle xtf_char(200), ZustaendigeStelle xtf_char(200)
    -> UUIDGenerator_2
    -> AttributeRemover_5
Note: EIB_OID
UUIDGenerator_2
    UUID_ATTR = EIB_OID
    -> AttributeRenamer
AttributeRenamer
    ATTR_LIST = xtf_id,EIB_XTF_ID,""
    -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> AttributeFilter_2
    MERGED -> FeatureMerger_2 [REQUESTOR]
Note: Nach Verbindlichkeit filtern
AttributeFilter_2
    ATTR_NAME = Verbindlichkeit
    ATTR_VALUES = <EMPTY>,<MISSING>,<NULL>,<UNFILTERED>,0
    0 -> AttributeRemover
AttributeRemover
    REMOVE_ATTRS = xtf_id,Objekt
    -> TimeStamper
TimeStamper
    FMT = FME Date (^Y^m^d)
    TIME_ATTR = _timestamp
    -> AttributeCreator
AttributeCreator
    ATTR_LIST = EIB_AUSSAGE_DE,Rechtskräftig festgestellte Waldgrenze,EIB_AUSSAGE_FR,Limite de la forêt, légalement fixée,LIN_PUBLIZIERTAB,@Value(_timestamp),EIB_PUBLIZIERTAB,@Value(_timestamp),VOR_PUBLIZIERTAB,@Value(_timestamp)
    -> LINIE (writer GEODATABASE_SDE_1)
    -> AttributeRemover_2
    -> AttributeRenamer_8
AttributeRenamer_8
    ATTR_TABLE:
      RENAME_SET_DEFAULT LIN_OID > id
      RENAME_SET_DEFAULT LIN_PUBLIZIERTAB > published_from
      RENAME_SET_DEFAULT EIB_OID > public_law_restriction_id
    -> ArcStroker
ArcStroker
    MAKE_POLY = No
    NUM = $(STROKER)
    STROKE_CHOICE = Number of Interpolated Edges
    TOLERANCE_VAL = 0.0
    STROKED -> GeometryRefiner
GeometryRefiner
    -> geometry (writer POSTGIS_2)
Note: Aggregation in legend_entry / https://agimine.easyredmine.com/projects/einfuehrung-oereb-server/wiki/Aggregation
geometry (writer POSTGIS_2)
    attributes: id varchar(80),PrimaryKey, law_status varchar(80), published_from date, geo_metadata varchar(80), public_law_restriction_id varchar(80), office_id varchar(80), liefereinheit int4
Note: OEREB2.LINIE
LINIE (writer GEODATABASE_SDE_1)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
AttributeRemover_2
    REMOVE_ATTRS = Genehmigung,Inkraftsetzung,Qualitaet,LIN_OID,Verbindlichkeit,Bemerkung,Datenverwaltungsstelle,ZustaendigeStelle,_timestamp,LIN_PUBLIZIERTAB,VOR_PUBLIZIERTAB
    -> Aggregator
Aggregator
    ACCUM_ATTRS_NAME = Yes
    GROUP_BY = EIB_XTF_ID EIB_OID EIB_AUSSAGE_DE EIB_AUSSAGE_FR EIB_PUBLIZIERTAB
    MODE = Attributes Only
    ORDERED = No
    SEP = ,
    AGGREGATE -> AttributeRemover_3
    AGGREGATE -> AttributeRemover_8
    AGGREGATE -> Counter
Counter
    CNT_ATTR = EIB_SORT
    DOMAIN = counter
    SCOPE = Global
    START = 1
    -> EIGENTUMSBESCHRAENKUNG (writer ORACLE8I_DB_1)
    -> AttributeRenamer_16
AttributeRenamer_16
    ATTR_TABLE:
      RENAME_SET_DEFAULT EIB_OID > plr_id
      RENAME_SET_DEFAULT EIB_PUBLIZIERTAB > published_from
      RENAME_SET_DEFAULT DAR_OID > view_service_id
      RENAME_SET_DEFAULT AMT_OID > office_id
      RENAME_SET_DEFAULT EIB_LEGENDESYMBOL_DE > symbol_url
    -> JSONTemplater_5 [ROOT]
Note: Information-Attribut als JSON-String / aufbauen.
JSONTemplater_5
    RESULT_ATTRIBUTE = information
    ROOT_QUERY_EXPR:
      {
          "fr": fme:get-attribute("EIB_AUSSAGE_FR"),
          "de": fme:get-attribute("EIB_AUSSAGE_DE")
      }
    VISIBLE_QUERY_VALIDATE = Yes
    -> AttributeKeeper_7
AttributeKeeper_7
    KEEP_ATTRS = plr_id,published_from,information
    -> AttributeCreator_14
AttributeCreator_14
    ATTR_TABLE:
      SET_TO topic = $(topic)
      SET_TO liefereinheit = $(LIEFEREINHEIT)
      SET_TO sub_theme = FME_NULL_VALUE
      SET_TO schema = $(schema)
      SET_TO view_service_id = $(DAR_OID)
      SET_TO office_id = $(AMT_OID)
      SET_TO symbol_url = $(LEGEND_BASEURL)
    -> Aggregator_10
public_law_restriction (writer POSTGRES_1)
    attributes: id varchar(80),PrimaryKey, information json, topic varchar(80), sub_theme json, other_theme varchar(80), type_code varchar(40), type_code_list varchar(80), law_status varchar(80), published_from date, view_service_id varchar(80), office_id varchar(80), liefereinheit int4
legend_entry (writer POSTGRES_2)
    attributes: id varchar(80),PrimaryKey, symbol varchar(80), symbol_url varchar(80), legend_text json, type_code varchar(40), type_code_list varchar(80), topic varchar(80), sub_theme json, other_theme varchar(80), view_service_id varchar(80), liefereinheit int4
Note: OEREB2.EIGENTUMSBESCHRAENKUNG
EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), STH_ID number(10,0), EIB_SORT number(10,0), EIB_LEGENDESYMBOL_DE nvarchar(1023), EIB_LEGENDESYMBOL_FR nvarchar(1023)
AttributeRemover_8
    REMOVE_ATTRS = EIB_AUSSAGE_DE,EIB_AUSSAGE_FR,EIB_PUBLIZIERTAB
    -> FeatureMerger_6 [SUPPLIER]
AttributeRemover_3
    REMOVE_ATTRS = EIB_XTF_ID,EIB_AUSSAGE_DE,EIB_AUSSAGE_FR,EIB_PUBLIZIERTAB
    -> AttributeCreator_2
    -> AttributeCreator_3
    -> AttributeCreator_4
Note: Waldgesetz (Bund) verlinken
AttributeCreator_2
    ATTR_LIST = VOR_OID,ch.admin.bk.sr.921.0
    -> UUIDGenerator_3
Note: Waldgesetz (Kanton) verlinken
AttributeCreator_3
    ATTR_LIST = VOR_OID,ch.be.sk.bsg.921.11
    -> UUIDGenerator_3
Note: Waldverordnung (Kanton) verlinken
AttributeCreator_4
    ATTR_LIST = VOR_OID,ch.be.sk.bsg.921.111
    -> UUIDGenerator_3
Note: HIV_ID
UUIDGenerator_3
    UUID_ATTR = HIV_ID
    -> HINVOR (writer ORACLE8I_DB_1)
    -> AttributeRemover_19
    -> AttributeRenamer_10
AttributeRemover_5
    REMOVE_ATTRS = xtf_id,Verbindlichkeit,Bemerkung
    -> FeatureMerger_4 [SUPPLIER]
    -> FeatureMerger_5 [SUPPLIER]
Note: WF_Einzelpunkt
DM16NplBE.Nutzungsplanung.WF_Einzelpunkt (reader ch.ehi.fme.Main_1)
    attributes: xtf_id xtf_char(200), Identifikator xtf_char(12), LageGen xtf_decimal(5,1), LageZuv xtf_char(255)
    -> AttributeValueMapper
AttributeValueMapper
    DIRECTION = Forward (Source To Destination)
    LUT = 0,1,1,2,2,3
    SRC = LageZuv
    VAL_ATTR = LAGEZUV
    -> AttributeRenamer_2
AttributeRenamer_2
    ATTR_LIST = LageGen,LAGEGEN,"",Identifikator,AV_IDENT,""
    -> NUPLWALD_WFWAEP (writer GEODATABASE_SDE_2)
    -> BulkAttributeRenamer_2
BulkAttributeRenamer_2
    ATTRCHOICE = All Attributes
    CASE_CHANGE_TYPE = lower
    MODE_CHOICE = RENAME
    PATTERN_ACTION_DISP = CASECHANGE
    -> nuplwald_wfwaep (writer POSTGIS_1)
Note: geodb.nuplwald_wfwaep
nuplwald_wfwaep (writer POSTGIS_1)
    attributes: bfsnr int2, gemname varchar(50), av_ident varchar(12), lagegen float4, lagezuv int2
Note: GEODB.NUPLWALD_WFWAEP
NUPLWALD_WFWAEP (writer GEODATABASE_SDE_2)
    attributes: BFSNR smallint, GEMNAME char(50), AV_IDENT char(12), LAGEGEN float, LAGEZUV smallint
Note: Amt
DM16NplBE.Nutzungsplanung.Amt (reader ch.ehi.fme.Main_1)
    attributes: xtf_id xtf_char(200), Name xtf_char(200), UID_Amt xtf_char(15), AmtImWeb xtf_char(200)
    -> UUIDGenerator_4
UUIDGenerator_4
    UUID_ATTR = AMT_ID
    -> AttributeRenamer_3
AttributeRenamer_3
    ATTR_LIST = AmtImWeb,AMTIMWEB,"",Name,AMTNAME,"",UID_Amt,UID_AMT,"",xtf_id,AMT_XTF_ID,""
    -> AttributeRemover_4
    -> FeatureMerger_4 [REQUESTOR]
    -> FeatureMerger_5 [REQUESTOR]
    -> AttributeRemover_6
FeatureMerger_4
    IGNORE_NULLS = Yes
    JOIN_KEYS = @Value(AMT_XTF_ID) @Value(ZustaendigeStelle) AUTO
    MERGE_TYPE = Attributes Only
    PROCESS_DUPS = No
    SUPPLIERS_FIRST = No
    SUPPLIER_PREFIX_DUMMY = YES
    MERGED -> NUPLWALD_WALDAMTT (writer GEODATABASE_SDE_2)
    MERGED -> BulkAttributeRenamer_3
FeatureMerger_5
    IGNORE_NULLS = Yes
    JOIN_KEYS = @Value(AMT_XTF_ID) @Value(Datenverwaltungsstelle) AUTO
    MERGE_TYPE = Attributes Only
    PROCESS_DUPS = No
    SUPPLIERS_FIRST = No
    SUPPLIER_PREFIX_DUMMY = YES
    MERGED -> NUPLWALD_WALDAMTT (writer GEODATABASE_SDE_2)
    MERGED -> BulkAttributeRenamer_3
Note: GEODB.NUPLWALD_WALDAMTT
NUPLWALD_WALDAMTT (writer GEODATABASE_SDE_2)
    attributes: BFSNR smallint, GEMNAME char(50), AMTNAME char(200), UID_AMT char(15), AMTIMWEB char(100), AMT_ID char(36)
BulkAttributeRenamer_3
    ATTRCHOICE = All Attributes
    CASE_CHANGE_TYPE = lower
    MODE_CHOICE = RENAME
    PATTERN_ACTION_DISP = CASECHANGE
    -> nuplwald_waldamtt (writer POSTGIS_1)
Note: geodb.nuplwald_waldamtt
nuplwald_waldamtt (writer POSTGIS_1)
    attributes: bfsnr int2, gemname varchar(50), amtname varchar(200), uid_amt varchar(15), amtimweb varchar(100), amt_id varchar(36)
AttributeRemover_6
    REMOVE_ATTRS = AMTNAME,UID_AMT,AMTIMWEB
    -> Dokument_vorbereiten [Amt]
AttributeRemover_4
    REMOVE_ATTRS = AMTNAME,UID_AMT,AMTIMWEB
    -> FeatureMerger_2 [SUPPLIER]
    -> FeatureMerger_3 [SUPPLIER]
Note: ZuständigeStelle joinen
FeatureMerger_2
    IGNORE_NULLS = Yes
    JOIN_KEYS = @Value(ZustaendigeStelle) @Value(AMT_XTF_ID) AUTO
    MERGE_TYPE = Attributes Only
    PROCESS_DUPS = No
    SUPPLIERS_FIRST = No
    SUPPLIER_PREFIX_DUMMY = YES
    MERGED -> AttributeRenamer_4
AttributeRenamer_4
    ATTR_LIST = AMT_ID,ZUSTAENDIG,"",EIB_OID,RVS_ID,""
    -> FeatureMerger_3 [REQUESTOR]
Note: Datenverwaltungsstelle joine
FeatureMerger_3
    IGNORE_NULLS = Yes
    JOIN_KEYS = @Value(Datenverwaltungsstelle) @Value(AMT_XTF_ID) AUTO
    MERGE_TYPE = Attributes Only
    PROCESS_DUPS = No
    SUPPLIERS_FIRST = No
    SUPPLIER_PREFIX_DUMMY = YES
    MERGED -> AttributeRenamer_5
AttributeRenamer_5
    ATTR_LIST = AMT_ID,DATENVERW,"",Bemerkung,BEMERK,"",Genehmigung,GENEHM,"",Inkraftsetzung,INKRAFT,""
    -> DateFormatter
DateFormatter
    DATE_ATTR = GENEHM,INKRAFT
    FMT = FME Date (%Y%m%d)
    INVALID_DATE_VALUE = FME_NULL_VALUE
    SRCFMT = Unknown - Automatic Detection
    -> AttributeValueMapper_2
Note: QUALITAET mappen / Interlis-Codelisten starten bei 0, / GeoDB-Wertetabellen bei 1!
AttributeValueMapper_2
    DIRECTION = Forward (Source To Destination)
    LUT = 0,1,1,2,2,3,3,4,4,5,5,6,6,7,7,8,8,9,9,10,10,11
    SRC = Qualitaet
    VAL_ATTR = QUALITAET
    -> AttributeValueMapper_3
Note: VERBINDLKT mappen / Interlis-Codelisten starten bei 0, / GeoDB-Wertetabellen bei 1!
AttributeValueMapper_3
    DIRECTION = Forward (Source To Destination)
    LUT = 0,1,1,2,2,3
    SRC = Verbindlichkeit
    VAL_ATTR = VERBINDLKT
    -> NUPLWALD_WFWAGRZ (writer GEODATABASE_SDE_2)
    -> BulkAttributeRenamer_4
BulkAttributeRenamer_4
    ATTRCHOICE = All Attributes
    CASE_CHANGE_TYPE = lower
    MODE_CHOICE = RENAME
    PATTERN_ACTION_DISP = CASECHANGE
    -> nuplwald_wfwagrz (writer POSTGIS_1)
Note: geodb.nuplwald_wfwagrz
nuplwald_wfwagrz (writer POSTGIS_1)
    attributes: bfsnr int2, gemname varchar(50), rvs_id varchar(100), genehm timestamp, inkraft timestamp, qualitaet int2, verbindlkt int2, bemerk varchar(80), datenverw varchar(36), zustaendig varchar(36)
Note: GEODB.NUPLWALD_WFWAGRZ
NUPLWALD_WFWAGRZ (writer GEODATABASE_SDE_2)
    attributes: BFSNR smallint, GEMNAME char(50), GENEHM date, INKRAFT date, QUALITAET smallint, VERBINDLKT smallint, BEMERK char(80), DATENVERW char(36), ZUSTAENDIG char(36), RVS_ID char(100)
Note: WF_FeststellungWaldPos
DM16NplBE.Nutzungsplanung.WF_FeststellungWaldPos (reader ch.ehi.fme.Main_1) [off]
    attributes: xtf_id xtf_char(200), Objekt xtf_char(200), TextOri xtf_decimal(5,1), TextHAli xtf_char(255), TextVAli xtf_char(255), TextSize xtf_char(255)
Note: OEREB2.HINWEIDOK
HINWEIDOK (writer ORACLE8I_DB_1) [off]
    attributes: HWD_ID nvarchar(128), HWD_XTF_ID nvarchar(128), HWD_LIEFEREINHEIT number(6,0), HWD_ARTNR nvarchar(255), VOR_OIDURSPRUNG nvarchar(128), VOR_OIDHINWEIS nvarchar(128)
Note: GEODB.NUPLWALD_WALDVRBT
NUPLWALD_WALDVRBT (writer GEODATABASE_SDE_2) [off]
    attributes: VERBINDLKT smallint, BEZ_DE char(100), BEZ_FR char(100)
document_reference (writer POSTGRES_6) [off]
    attributes: id varchar(80),PrimaryKey, document_id varchar(80), reference_document_id varchar(80), article_numbers varchar(80), liefereinheit int4
Note: GEODB.NUPLWALD_WALDQLT
NUPLWALD_WALDQLT (writer GEODATABASE_SDE_2) [off]
    attributes: QUALITAET smallint, BEZ_DE char(100), BEZ_FR char(100)
Note: GEODB.NUPLWALD_LAGEZUVT
NUPLWALD_LAGEZUVT (writer GEODATABASE_SDE_2) [off]
    attributes: CODE smallint, BEZ_DE char(100), BEZ_FR char(100)
Note: EXCEL_AMT
AMT (reader XLSXR_1)
    attributes: AMT_OID char(20), AMT_NAME_DE char(73), AMT_NAME_FR char(73), AMT_AMTIMWEB_DE char(101), AMT_AMTIMWEB_FR char(102), AMT_LIEFEREINHEIT number(6,0), AMT_SPRACHE char(6)
    -> TestFilter_3
TestFilter_3
    DEFAULT_VALUE = <UNFILTERED>
    TEST_LIST = "BOOL_OP,OR,COMPOSITE_TEST,""""""<Unused>"""""",TEST_CLAUSE,TEST @Value(AMT_OID) = $(AMT_OID_BASE)",LIEFEREINHEIT
    LIEFEREINHEIT -> AttributeManager_2
AttributeManager_2
    ATTR_TABLE = SET_TO AMT_OID = $(AMT_OID)
    -> AttributeKeeper
AttributeKeeper
    KEEP_ATTRS = AMT_NAME_DE,AMT_OID,AMT_NAME_FR,AMT_AMTIMWEB_DE,AMT_AMTIMWEB_FR
    -> AttributeRenamer_7
    -> AMT (writer ORACLE8I_DB_1)
AMT (writer ORACLE8I_DB_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(6,0), AMT_LINE1 nvarchar(80), AMT_LINE2 nvarchar(80), AMT_STREET nvarchar(100), AMT_NUMBER nvarchar(7), AMT_POSTALCODE nvarchar(4), AMT_CITY nvarchar(60)
AttributeRenamer_7
    ATTR_TABLE:
      RENAME_SET_DEFAULT AMT_OID > id
      RENAME_SET_DEFAULT AMT_AMTIMWEB_DE > office_at_web
    -> JSONTemplater [ROOT]
Note: Name-Attribut als JSON-String / aufbauen.
JSONTemplater
    RESULT_ATTRIBUTE = name
    ROOT_QUERY_EXPR:
      {
          "fr": fme:get-attribute("AMT_NAME_FR"),
          "de": fme:get-attribute("AMT_NAME_DE")
      }
    VISIBLE_QUERY_VALIDATE = Yes
    -> office (writer POSTGRES_7)
office (writer POSTGRES_7)
    attributes: id varchar(80),PrimaryKey, name json, office_at_web varchar(80), uid varchar(12), line1 varchar(80), line2 varchar(80), street varchar(80), number varchar(80), postal_code int4, city varchar(80), liefereinheit int4,BTree
Note: Dokument
DM16NplBE.Nutzungsplanung.Dokument (reader ch.ehi.fme.Main_1)
    attributes: xtf_id xtf_char(200), Art_Doku xtf_char(255), Titel xtf_char(200), OffiziellerTitel xtf_char(200), Abkuerzung xtf_char(20), OffizielleNr xtf_char(20), Gemeinde xtf_int32, Dokument xtf_char(100), ZustaendigeStelle xtf_char(200)
    -> Dokument_vorbereiten [Dokument]
Note: Dokument vorbereiten
Dokument_vorbereiten: Dokument vorbereiten
    ABKUERZUNG = @Value(Abkuerzung)
    AMT_ID = @Value(AMT_ID)
    AMT_XTF_ID = @Value(AMT_XTF_ID)
    ART_DOKU = @Value(Art_Doku)
    DOKUMENT = @Value(Dokument)
    GEMEINDE = @Value(Gemeinde)
    OFFIZIELLENR = @Value(OffizielleNr)
    OFFIZIELLERTITEL = @Value(OffiziellerTitel)
    TITEL = @Value(Titel)
    WALDGRENZEN_VERFUEGUNG_DE = $(WALDGRENZEN_VERFUEGUNG_DE)
    WALDGRENZEN_VERFUEGUNG_FR = $(WALDGRENZEN_VERFUEGUNG_FR)
    XTF_ID = @Value(xtf_id)
    ZUSTAENDIGESTELLE = @Value(ZustaendigeStelle)
    Alle_Dokumente -> FeatureMerger_7 [SUPPLIER]
    Alle_Dokumente -> HINWEIDOK-IDs_ersetzen [AlleDokumente]
    Alle_Dokumente -> FeatureMerger_12 [REQUESTOR]
Note: WF_FeststellungWaldRV
DM16NplBE.Nutzungsplanung.WF_FeststellungWaldRV (reader ch.ehi.fme.Main_1)
    attributes: xtf_id xtf_char(200), Typ xtf_char(200), Vorschrift xtf_char(200), ArtikelNr xtf_char(40)
    -> AttributeRemover_7
AttributeRemover_7
    REMOVE_ATTRS = xtf_id
    -> AttributeRenamer_6
AttributeRenamer_6
    ATTR_LIST = ArtikelNr,HIV_ARTNR,""
    -> FeatureMerger_6 [REQUESTOR]
FeatureMerger_6
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeRemover_9
AttributeRemover_9
    REMOVE_ATTRS = Typ,EIB_XTF_ID
    -> FeatureMerger_7 [REQUESTOR]
FeatureMerger_7
    IGNORE_NULLS = Yes
    JOIN_KEYS = @Value(Vorschrift) @Value(VOR_XTF_ID) AUTO
    MERGE_TYPE = Attributes Only
    PROCESS_DUPS = No
    SUPPLIERS_FIRST = No
    SUPPLIER_PREFIX_DUMMY = YES
    MERGED -> AttributeRemover_10
AttributeRemover_10
    REMOVE_ATTRS = Vorschrift,VOR_XTF_ID,Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset,AMT_XTF_ID,ZUSTAENDIG
    -> FeatureMerger_11 [REQUESTOR]
    -> UUIDGenerator_7
Note: HinweisWeitereDokumente
DM16NplBE.Nutzungsplanung.HinweisWeitereDokumente (reader ch.ehi.fme.Main_1)
    attributes: xtf_id xtf_char(200), Ursprung xtf_char(200), Hinweis xtf_char(200), ArtikelNr xtf_char(40), Ordnungsnummer xtf_int32
    -> HINWEIDOK-IDs_ersetzen [HinweisWeitereDokumente]
Note: HiinweisWeitereDokumente: / alle IDs ersetzen durch UUIDs / (VOR_OID)
HINWEIDOK-IDs_ersetzen: HINWEIDOK-IDs ersetzen
    ARTIKELNR = @Value(ArtikelNr)
    HINWEIS = @Value(Hinweis)
    ORDNUNGSNUMMER = @Value(Ordnungsnummer)
    URSPRUNG = @Value(Ursprung)
    VOR_OID = @Value(VOR_OID)
    VOR_XTF_ID = @Value(VOR_XTF_ID)
    HINWEIDOK_ID_ersetzt -> HINWEIDOK_flachdruecken [HINWEIDOK]
Note: HINWEIDOK flachdruecken / (mit Views aus Verschnitt- / funktion)
HINWEIDOK_flachdruecken: HINWEIDOK flachdruecken
    HINWEIDOK_flach -> FeatureMerger_11 [SUPPLIER]
FeatureMerger_11
    GEOM_TYPE = Build Polygons
    IGNORE_NULLS = Yes
    JOIN_KEYS = @Value(VOR_OID) @Value(VOR_OIDURSPRUNG) AUTO
    LIST_NAME = duplicates
    MERGE_TYPE = Attributes Only
    PROCESS_DUPS = Yes
    SUPPLIERS_FIRST = No
    SUPPLIER_PREFIX_DUMMY = YES
    MERGED -> AttributeRemover_15
AttributeRemover_15
    REMOVE_ATTRS = HIV_ARTNR,VOR_OID,VOR_OIDURSPRUNG,VOR_OIDHINWEIS
    -> ListExploder
ListExploder
    INDEX_ATTR = _element_index
    LIST_ATTR = duplicates{}
    MODE = List Elements and Original Attributes
    LIST_FOUND -> AttributeRemover_16
AttributeRemover_16
    REMOVE_ATTRS = VOR_OIDURSPRUNG,_element_index
    -> AttributeRenamer_12
AttributeRenamer_12
    ATTR_LIST = VOR_OIDHINWEIS,VOR_OID,""
    -> Aggregator_3
Note: Es kann Duplikate geben / (v.a. in Thun)
Aggregator_3
    ACCUM_ATTRS_NAME = Yes
    GROUP_BY = EIB_OID VOR_OID
    MODE = Attributes Only
    ORDERED = No
    SEP = ,
    AGGREGATE -> UUIDGenerator_7
UUIDGenerator_7
    UUID_ATTR = HIV_ID
    -> AttributeRemover_18
    -> AttributeRemover_19
    -> DuplicateRemover_3
Note: Alle Duplikate entfernen
DuplicateRemover_3
    KEYATTR = EIB_OID VOR_OID
    UNIQUE -> HINVOR (writer ORACLE8I_DB_1)
    UNIQUE -> AttributeRenamer_10
AttributeRenamer_10
    ATTR_TABLE:
      RENAME_SET_DEFAULT HIV_ID > id
      RENAME_SET_DEFAULT EIB_OID > public_law_restriction_id
      RENAME_SET_DEFAULT VOR_OID > document_id
    -> public_law_restriction_document (writer POSTGRES_5)
public_law_restriction_document (writer POSTGRES_5)
    attributes: id varchar(80),PrimaryKey, public_law_restriction_id varchar(80), document_id varchar(80), article_numbers varchar(80), liefereinheit int4
Note: OEREB2.HINVOR
HINVOR (writer ORACLE8I_DB_1)
    attributes: HIV_ID nvarchar(128), HIV_XTF_ID nvarchar(128), HIV_ARTNR nvarchar(255), HIV_LIEFEREINHEIT number(6,0), EIB_OID nvarchar(128), VOR_OID nvarchar(128)
AttributeRemover_19
    REMOVE_ATTRS = HIV_ID
    -> FeatureMerger_13 [REQUESTOR]
AttributeRemover_18
    REMOVE_ATTRS = HIV_ARTNR,EIB_OID,HIV_ID
    -> Aggregator_2
Aggregator_2
    ACCUM_ATTRS_NAME = Yes
    GROUP_BY = VOR_OID
    MODE = Attributes Only
    ORDERED = No
    SEP = ,
    AGGREGATE -> FeatureMerger_12 [SUPPLIER]
FeatureMerger_12
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> FeatureMerger_13 [SUPPLIER]
    MERGED -> AttributeRemover_11
AttributeRemover_11
    REMOVE_ATTRS = Art_Doku,Gemeinde,Dokument,ZustaendigeStelle,AMT_XTF_ID,ZUSTAENDIG
    -> DuplicateRemover_2
Note: Alle Duplikate entfernen
DuplicateRemover_2
    KEYATTR = VOR_XTF_ID VOR_TITEL_DE VOR_OFFIZIELLERTITEL_DE VOR_ABKUERZUNG_DE VOR_OFFIZIELLENR VOR_OID VOR_PUBLIZIERTAB VOA_ID VOR_TITEL_FR VOR_OFFIZIELLERTITEL_FR VOR_ABKUERZUNG_FR VOR_TEXTIMWEB_DE VOR_TEXTIMWEB_FR filecopy_source_dataset filecopy_dest_dataset
    UNIQUE -> TestFilter
    UNIQUE -> AttributeRenamer_9
    UNIQUE -> VORSCHRIFT (writer ORACLE8I_DB_1)
AttributeRenamer_9
    ATTR_TABLE:
      RENAME_SET_DEFAULT VOR_OID > id
      RENAME_SET_DEFAULT VOR_PUBLIZIERTAB > published_from
      RENAME_SET_DEFAULT AMT_OID > office_id
    -> JSONTemplater_6 [ROOT]
Note: text_at_web-Attribut als JSON-String / aufbauen.
JSONTemplater_6
    RESULT_ATTRIBUTE = text_at_web
    ROOT_QUERY_EXPR:
      {
          "fr": fme:get-attribute("VOR_TEXTIMWEB_FR"),
          "de": fme:get-attribute("VOR_TEXTIMWEB_DE")
      }
    VISIBLE_QUERY_VALIDATE = Yes
    -> AttributeValueMapper_5
Note: document_type-Attribut / mappen
AttributeValueMapper_5
    DIRECTION = Forward (Source To Destination)
    LUT = 1,LegalProvision,2,Law,3,Hint
    SRC = VOA_ID
    VAL_ATTR = document_type
    -> AttributeCreator_12
Note: type-Attribut ist wohl immer "document"
AttributeCreator_12
    ATTR_TABLE = SET_TO type = document
    -> JSONTemplater_3 [ROOT]
Note: Title-Attribut als JSON-String / aufbauen.
JSONTemplater_3
    RESULT_ATTRIBUTE = title
    ROOT_QUERY_EXPR:
      {
          "fr": fme:get-attribute("VOR_TITEL_FR"),
          "de": fme:get-attribute("VOR_TITEL_DE")
      }
    VISIBLE_QUERY_VALIDATE = Yes
    -> document (writer POSTGRES_4)
    -> document_base (writer POSTGRES_3)
document_base (writer POSTGRES_3)
    attributes: id varchar(80),PrimaryKey, text_at_web json, law_status varchar(80), published_from date, type varchar(80), liefereinheit int4
document (writer POSTGRES_4)
    attributes: document_type varchar(80), title json, official_title json, abbreviation json, official_number varchar(80), canton varchar(2), municipality int4, file varchar(80), id varchar(80),PrimaryKey, office_id varchar(80), liefereinheit int4
Note: Standard-Verfügung nicht kopieren
TestFilter
    DEFAULT_VALUE = <UNFILTERED>
    TEST_LIST:
      "BOOL_OP,OR,COMPOSITE_TEST,""""""<Unused>"""""",TEST_CLAUSE,TEST @Value(VOR_TEXTIMWEB_DE) = $(WALDGRENZEN_VERFUEGUNG_DE)
      TEST @Value(VOR_TEXTIMWEB_FR) = $(WALDGRENZEN_VERFUEGUNG_FR)",STANDARDVERFUEGUNG
    STANDARDVERFUEGUNG -> TestFilter_STANDARDVERFUEGUNG
    <UNFILTERED> -> filecopy (writer FILECOPY_1)
TestFilter_STANDARDVERFUEGUNG: Logger
    LOG_FEATURE = LOG_ONLY
    MAXCOORDS = 20
    MAXFEATS = 20
    MESSAGE = Standardverfügung; wird nicht kopiert.
    SEVERITY = INFO
filecopy (writer FILECOPY_1)
Note: OEREB2.VORSCHRIFT
VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)
Note: Merged = REVO und HINW / NotMerged = GEGR
FeatureMerger_13
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> AttributeRenamer_13
    NOT_MERGED -> Tester
Note: Default-RV rausfiltern
Tester
    BOOL_OP = OR
    TEST_CLAUSE = "TEST @Value(VOR_OID) = "
    FAILED -> Joiner
Note: GEGR aus der DB holen. Die / werden separat importiert.
Joiner
    ADDED_FIELDS = VOR_TEXTIMWEB_DE VOR_TITEL_DE VOR_OFFIZIELLERTITEL_DE VOR_ABKUERZUNG_DE VOR_OFFIZIELLENR VOA_ID
    CACHE_SIZE = 5000
    DATASET = $(OEREB2_DATABASE)
    FORMAT = ORACLE8I_DB
    JOIN_KEYS = VOR_OID VOR_OID
    MATCH_RULE_DISPLAY = Must Match Exactly One (1:1)
    ORACLE8I_DB_PASSWORD = $(OEREB2_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(OEREB2_USERNAME)
    PREFETCH_EXHAUSTIVE = Yes
    TABLE = OEREB2.VORSCHRIFT
    JOINED -> AttributeRenamer_13
AttributeRenamer_13
    ATTR_LIST = EIB_OID,RVS_ID,"",VOR_TITEL_DE,TITEL,"",VOR_OFFIZIELLERTITEL_DE,OFFIZTITEL,"",VOR_ABKUERZUNG_DE,ABKUERZUNG,"",VOR_OFFIZIELLENR,OFFIZNR,"",VOR_TEXTIMWEB_DE,DOKUMENT,"",HIV_ARTNR,ARTIKELNR,""
    -> AttributeValueMapper_7
Note: ART aus VOA_ID mappen
AttributeValueMapper_7
    DIRECTION = Forward (Source To Destination)
    LUT = 1,Rechtsvorschrift,2,Gesetzliche Grundlage,3,Hinweis
    SRC = VOA_ID
    VAL_ATTR = ART
    -> Sorter
Sorter
    SORT_PARM = RVS_ID ALPHA ASCENDING ART ALPHA DESCENDING
    SORTED -> AttributeRemover_12
AttributeRemover_12
    REMOVE_ATTRS = AMT_XTF_ID,VOR_OID,VOA_ID,_matched_records,VOR_XTF_ID,Art_Doku,Gemeinde,Dokument,ZustaendigeStelle,VOR_PUBLIZIERTAB,VOR_TITEL_FR,VOR_OFFIZIELLERTITEL_FR,VOR_ABKUERZUNG_FR,VOR_TEXTIMWEB_FR,filecopy_source_dataset,filecopy_dest_dataset
    -> DuplicateRemover
Note: Alle Duplikate entfernen
DuplicateRemover
    KEYATTR = RVS_ID ARTIKELNR DOKUMENT TITEL OFFIZTITEL ABKUERZUNG OFFIZNR ZUSTAENDIG ART
    UNIQUE -> NUPLWALD_WALDRVST (writer GEODATABASE_SDE_2)
    UNIQUE -> BulkAttributeRenamer
BulkAttributeRenamer
    ATTRCHOICE = All Attributes
    CASE_CHANGE_TYPE = lower
    MODE_CHOICE = RENAME
    PATTERN_ACTION_DISP = CASECHANGE
    -> nuplwald_waldrvst (writer POSTGIS_1)
Note: nuplwald_waldrvst
nuplwald_waldrvst (writer POSTGIS_1)
    attributes: bfsnr int2, gemname varchar(50), rvs_id varchar(100), art varchar(40), titel varchar(200), offiztitel varchar(200), abkuerzung varchar(20), offiznr varchar(20), dokument varchar(1023), artikelnr varchar(40), ordnnr int2, zustaendig varchar(36)
Note: GEODB.NUPLWALD_WALDRVST
NUPLWALD_WALDRVST (writer GEODATABASE_SDE_2)
    attributes: BFSNR smallint, GEMNAME char(50), RVS_ID char(100), ART char(40), TITEL char(200), OFFIZTITEL char(200), ABKUERZUNG char(20), OFFIZNR char(20), DOKUMENT char(100), ARTIKELNR char(40), ORDNNR smallint, ZUSTAENDIG char(36)

Bookmark: Aggregation für TypeCode
Aggregator_10
    ACCUM_ATTRS_NAME = Use Attributes From One Feature
    AGGREGATE_TYPE = Homogeneous Collection (If Possible)
    GROUP_BY = information published_from liefereinheit topic sub_theme symbol_url schema view_service_id office_id
    LIST_ATTRS_TO_INCLUDE = plr_id
    LIST_NAME = plr_ids
    MODE = Geometry - Assemble One Level
    ORDERED = No
    SEP = ,
    AGGREGATE -> UUIDGenerator_5
UUIDGenerator_5
    UUID_ATTR = legend_entry_id
    -> UUIDGenerator_8
UUIDGenerator_8
    UUID_ATTR = type_code
    -> UUIDGenerator_9
UUIDGenerator_9
    UUID_ATTR = type_code_list
    -> AttributeManager
    -> AttributeRenamer_11
AttributeManager
    ATTR_TABLE:
      REMOVE symbol_url
      REMOVE plr_id
      REMOVE legend_entry_id
    -> ListExploder_2
ListExploder_2
    ATTR_ACCUM_MODE = Merge List Attributes
    ATTR_CONFLICT_RES = Use List Attribute Values
    INDEX_ATTR = _element_index
    LIST_ATTR = plr_ids{}
    ELEMENTS -> AttributeRenamer_15
AttributeRenamer_15
    ATTR_TABLE = RENAME_SET_DEFAULT plr_id > id
    -> public_law_restriction (writer POSTGRES_1)
AttributeRenamer_11
    ATTR_TABLE = RENAME_SET_DEFAULT information > legend_text
    -> AttributeKeeper_11
AttributeKeeper_11
    KEEP_ATTRS = legend_text,schema,topic,symbol_url,sub_theme,view_service_id,legend_entry_id,type_code,liefereinheit,type_code_list
    -> AttributeRenamer_14
    -> AttributeKeeper_8
AttributeRenamer_14
    ATTR_TABLE = RENAME_SET_DEFAULT legend_entry_id > id
    -> FeatureMerger_9 [REQUESTOR]
AttributeKeeper_8
    KEEP_ATTRS = symbol_url
    -> Aggregator_4
Aggregator_4
    ACCUM_ATTRS_NAME = Use Attributes From One Feature
    AGGREGATE_TYPE = Homogeneous Collection (If Possible)
    GROUP_BY = symbol_url
    MODE = Geometry - Assemble One Level
    ORDERED = No
    SEP = ,
    AGGREGATE -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = symbol_binary
    TARGET_ATTR_ENCODING = auto-detect
    TARGET_URL = @Value(symbol_url)
    TRANSFER_TIMEOUT_LENGTH = 90
    USE_COOKIES = No
    VERIFY_SSL_CERTIFICATES = Yes
    -> BinaryEncoder_2
BinaryEncoder_2
    ATTR_TO_ENCODE = symbol_binary
    DEST_ATTR = symbol
    ENCODING_TYPE = Base64
    -> AttributeKeeper_9
AttributeKeeper_9
    KEEP_ATTRS = symbol_url,symbol
    -> FeatureMerger_9 [SUPPLIER]
FeatureMerger_9
    ATTR_ACCUM_MODE = Merge Supplier
    ATTR_CONFLICT_RES = Use Requestor
    IGNORE_NULLS = No
    JOIN_KEYS = @Value(symbol_url) @Value(symbol_url) AUTO
    MERGE_TYPE = Attributes Only
    PROCESS_DUPS = NO
    REJECT_NULL_MISSING_KEYS = No
    SUPPLIERS_FIRST = No
    MERGED -> AttributeKeeper_6
AttributeKeeper_6
    KEEP_ATTRS = schema,sub_theme,type_code,id,topic,type_code_list,liefereinheit,legend_text,symbol_url,symbol,view_service_id
    -> legend_entry (writer POSTGRES_2)

FME custom transformer HINWEIDOK flachdruecken

HINWEIDOK (input)
    -> InlineQuerier [HINWEIDOK]
Note: SQL-Query stammt aus dem / View VIW_VORCHAIN1 der / Verschnittfunktion
InlineQuerier
    QUERY_DEF:
      VIW_VORCHAIN1,SELECT HINWEIDOK.VOR_OIDURSPRUNG,
        HINWEIDOK.VOR_OIDHINWEIS,
        HINWEIDOK1.VOR_OIDHINWEIS AS VOR_OIDHINWEIS1,
        HINWEIDOK2.VOR_OIDHINWEIS AS VOR_OIDHINWEIS2
      FROM HINWEIDOK
      LEFT JOIN HINWEIDOK HINWEIDOK1
      ON HINWEIDOK.VOR_OIDHINWEIS = HINWEIDOK1.VOR_OIDURSPRUNG
      LEFT JOIN HINWEIDOK HINWEIDOK2
      ON HINWEIDOK1.VOR_OIDHINWEIS = HINWEIDOK2.VOR_OIDURSPRUNG,FIRST
    QUERY_SCHEMA = VIW_VORCHAIN1,VOR_OIDURSPRUNG,text,VOR_OIDHINWEIS,text,VOR_OIDHINWEIS1,text,VOR_OIDHINWEIS2,text
    TABLE_DEF = HINWEIDOK,ARTIKELNR,text,ORDNNR,text,VOR_OIDURSPRUNG,text,VOR_OIDHINWEIS,text
    VIW_VORCHAIN1 -> InlineQuerier_2 [VIW_VORCHAIN1]
Note: SQL-Query stammt aus dem / View VIW_VORCHAIN2 der / Verschnittfunktion
InlineQuerier_2
    QUERY_DEF:
      VIW_VORCHAIN2,  select "VOR_OIDURSPRUNG","OIDFROM","OIDTO" from
      (select
      VOR_OIDURSPRUNG ,VOR_OIDURSPRUNG oidfrom,  VOR_OIDHINWEIS oidto from VIW_VORCHAIN1
      union
      select
      VOR_OIDURSPRUNG,VOR_OIDHINWEIS, VOR_OIDHINWEIS1 from VIW_VORCHAIN1
      union
      select
      VOR_OIDURSPRUNG,VOR_OIDHINWEIS1, VOR_OIDHINWEIS2 from VIW_VORCHAIN1
      )
      where oidfrom is not null and
      oidto is not null;,FIRST
    QUERY_SCHEMA = VIW_VORCHAIN2,VOR_OIDURSPRUNG,text,oidfrom,text,oidto,text
    TABLE_DEF = VIW_VORCHAIN1,VOR_OIDURSPRUNG,text,VOR_OIDHINWEIS,text,VOR_OIDHINWEIS1,text,VOR_OIDHINWEIS2,text
    VIW_VORCHAIN2 -> AttributeRenamer_11
AttributeRenamer_11
    ATTR_LIST = oidto,VOR_OIDHINWEIS,""
    -> AttributeRemover_14
AttributeRemover_14
    REMOVE_ATTRS = oidfrom
    -> HINWEIDOK_flach (output)
HINWEIDOK_flach (output)

FME custom transformer HINWEIDOK-IDs ersetzen

Parameters:
- ARTIKELNR = @Value(ArtikelNr)   # ArtikelNr
- ORDNUNGSNUMMER = @Value(Ordnungsnummer)   # Ordnungsnummer
- VOR_OID = @Value(VOR_OID)   # Vor Oid
- URSPRUNG = @Value(Ursprung)   # Ursprung
- HINWEIS = @Value(Hinweis)   # Hinweis
- VOR_XTF_ID = @Value(VOR_XTF_ID)   # Vor Xtf Id

AlleDokumente (input)
    -> AttributeRemover_9
AttributeRemover_9
    REMOVE_ATTRS = Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset
    -> FeatureMerger_5 [SUPPLIER]
    -> FeatureMerger_6 [SUPPLIER]
HinweisWeitereDokumente (input)
    -> AttributeRenamer_5
AttributeRenamer_5
    ATTR_LIST = ArtikelNr,ARTIKELNR,"",Ordnungsnummer,ORDNNR,""
    -> AttributeRemover_7
AttributeRemover_7
    REMOVE_ATTRS = xtf_id
    -> FeatureMerger_5 [REQUESTOR]
FeatureMerger_5
    IGNORE_NULLS = Yes
    JOIN_KEYS = @Value(Ursprung) @Value(VOR_XTF_ID) AUTO
    MERGE_TYPE = Attributes Only
    PROCESS_DUPS = No
    SUPPLIERS_FIRST = No
    SUPPLIER_PREFIX_DUMMY = YES
    MERGED -> AttributeRenamer_6
AttributeRenamer_6
    ATTR_LIST = VOR_OID,VOR_OIDURSPRUNG,""
    -> AttributeRemover_12
AttributeRemover_12
    REMOVE_ATTRS = Ursprung,VOR_XTF_ID
    -> FeatureMerger_6 [REQUESTOR]
FeatureMerger_6
    IGNORE_NULLS = Yes
    JOIN_KEYS = @Value(Hinweis) @Value(VOR_XTF_ID) AUTO
    MERGE_TYPE = Attributes Only
    PROCESS_DUPS = No
    SUPPLIERS_FIRST = No
    SUPPLIER_PREFIX_DUMMY = YES
    MERGED -> AttributeRenamer_8
AttributeRenamer_8
    ATTR_LIST = VOR_OID,VOR_OIDHINWEIS,""
    -> AttributeRemover_13
AttributeRemover_13
    REMOVE_ATTRS = Hinweis,VOR_XTF_ID
    -> HINWEIDOK_ID_ersetzt (output)
HINWEIDOK_ID_ersetzt (output)

FME custom transformer Dokument vorbereiten

Parameters:
- OFFIZIELLERTITEL = @Value(OffiziellerTitel)   # OffiziellerTitel
- TITEL = @Value(Titel)   # Titel
- XTF_ID = @Value(xtf_id)   # Xtf Id
- DOKUMENT = @Value(Dokument)   # Dokument
- ABKUERZUNG = @Value(Abkuerzung)   # Abkuerzung
- GEMEINDE = @Value(Gemeinde)   # Gemeinde
- ART_DOKU = @Value(Art_Doku)   # Art Doku
- ZUSTAENDIGESTELLE = @Value(ZustaendigeStelle)   # ZustaendigeStelle
- OFFIZIELLENR = @Value(OffizielleNr)   # OffizielleNr
- AMT_XTF_ID = @Value(AMT_XTF_ID)   # Amt Xtf Id
- AMT_ID = @Value(AMT_ID)   # Amt Id
- WALDGRENZEN_VERFUEGUNG_DE =
- WALDGRENZEN_VERFUEGUNG_FR =

Dokument (input)
    -> AttributeRemover_2
AttributeRemover_2
    REMOVE_ATTRS = AMT_XTF_ID,AMT_ID
    -> UUIDGenerator_5
Note: VOR_OID
UUIDGenerator_5
    UUID_ATTR = VOR_OID
    -> TimeStamper_2
TimeStamper_2
    FMT = FME Date (^Y^m^d)
    TIME_ATTR = VOR_PUBLIZIERTAB
    -> AttributeValueMapper
AttributeValueMapper
    DIRECTION = Forward (Source To Destination)
    LUT = 0,1,1,3
    SRC = Art_Doku
    VAL_ATTR = VOA_ID
    -> AttributeRenamer_4
AttributeRenamer_4
    ATTR_LIST = xtf_id,VOR_XTF_ID,"",Titel,VOR_TITEL_DE,"",OffiziellerTitel,VOR_OFFIZIELLERTITEL_DE,"",Abkuerzung,VOR_ABKUERZUNG_DE,"",OffizielleNr,VOR_OFFIZIELLENR,""
    -> AttributeCreator_4
AttributeCreator_4
    ATTR_LIST = VOR_TITEL_FR,@Value(VOR_TITEL_DE),VOR_OFFIZIELLERTITEL_FR,@Value(VOR_OFFIZIELLERTITEL_DE),VOR_ABKUERZUNG_FR,@Value(VOR_ABKUERZUNG_DE),ZustaendigeStelle,@Value(ZustaendigeStelle),Dokument,@Value(Dokument),Gemeinde,@Value(Gemeinde)
    -> PythonCaller
PythonCaller
    NEW_ATTRIBUTES = VOR_TEXTIMWEB_DE VOR_TEXTIMWEB_FR filecopy_source_dataset filecopy_dest_dataset
    PYTHONSOURCE:
      import fmeobjects
      import os

      def processFeature(feature):
          filename = feature.getAttribute('Dokument')

          # Die Standard-Verfügung wird nicht mitgeliefert und nicht mitkopiert.
          # Hier muss nur die URL aus der Config eingetragen werden.
          if filename.lower() in ('verfuegung.pdf','decision.pdf'):
              outputURL_de = FME_MacroValues['WALDGRENZEN_VERFUEGUNG_DE']
              outputURL_fr = FME_MacroValues['WALDGRENZEN_VERFUEGUNG_FR']
          else:
              outputURL_de = FME_MacroValues['OUTPUT_RV_URL'] + filename
              outputURL_fr = FME_MacroValues['OUTPUT_RV_URL'] + filename

          inputFile = os.path.join(FME_MacroValues['INPUT_RV_DIR'], filename)
          inputFile = inputFile.replace('\\','/')

          outputDir = FME_MacroValues['OUTPUT_RV_DIR'].replace('\\','/')

          feature.setAttribute('VOR_TEXTIMWEB_DE', outputURL_de)
          feature.setAttribute('VOR_TEXTIMWEB_FR', outputURL_fr)
          feature.setAttribute('filecopy_source_dataset', inputFile)
          feature.setAttribute('filecopy_dest_dataset', outputDir)
    PYTHONSYMBOL = processFeature
    -> FeatureMerger [REQUESTOR]
Amt (input)
    -> AttributeRemover
AttributeRemover
    REMOVE_ATTRS = OffiziellerTitel,ZustaendigeStelle,Titel,Abkuerzung,OffizielleNr,Gemeinde,xtf_id,Dokument,Art_Doku
    -> AttributeRenamer
AttributeRenamer
    ATTR_LIST = AMT_ID,ZUSTAENDIG,""
    -> FeatureMerger [SUPPLIER]
FeatureMerger
    IGNORE_NULLS = Yes
    JOIN_KEYS = @Value(ZustaendigeStelle) @Value(AMT_XTF_ID) AUTO
    MERGE_TYPE = Attributes Only
    PROCESS_DUPS = No
    SUPPLIERS_FIRST = No
    SUPPLIER_PREFIX_DUMMY = YES
    MERGED -> AttributeManager
AttributeManager
    ATTR_TABLE:
      SET_TO VOR_OFFIZIELLERTITEL_DE = FME_NULL_VALUE
      SET_TO VOR_OFFIZIELLERTITEL_FR = FME_NULL_VALUE
    -> Alle_Dokumente (output)
Alle_Dokumente (output)
