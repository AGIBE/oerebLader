FME workspace s24_import_transfer_xtf.fmw
Startup Python:
      # -*- coding: utf-8 -*-
      import fmeobjects

      #=======================================================================================
      # Mehrsprachige Felder in INTERLIS2 behandeln
      def processMultilangFields(feature):

          multilangFields = feature.getAttribute('multilangfields').split(",")

          for mlField in multilangFields:
              content_de = ""
              content_fr = ""
              content_it = ""

              att_Language_list = feature.getAttribute(mlField + '{0}.LocalisedText{}.Language')
              att_Text_list = feature.getAttribute(mlField + '{0}.LocalisedText{}.Text')

              # wenn das Multilang-Feld nicht abgefüllt ist, soll es nicht bearbeitet werden
              if att_Language_list is not None:

                      for i in range(len(att_Language_list)):
                          if att_Language_list[i]=="de":
                              content_de = att_Text_list[i]
                          if att_Language_list[i]=="fr":
                              content_fr = att_Text_list[i]
                          if att_Language_list[i]=="it":
                              content_it = att_Text_list[i]

                      # Wenn der Text nur in einer Sprache vorhanden ist, wird er auch für die andere Sprache verwendet
                      if content_de == "":
                          content_de = content_fr
                      if content_de == "":
                          content_de = content_it
                      if content_fr == "":
                          content_fr = content_de
                      if content_fr == "":
                          content_fr = content_it

              feature.setAttribute(mlField + "_DE", content_de)
              feature.setAttribute(mlField + "_FR", content_fr)

Parameters:
- MODELLABLAGE = %XTF_DIR;http://models.interlis.ch/;C:\Program Files (x86)\FME/plugins/interlis2/ilimodels;C:\Program Files (x86)\FME/plugins/interlis2/ili22models   # Modellablage
- XTF_FILE = D:\Daten\OEREBK\Bundesthemen\kbsoev\ch.bav.kataster-belasteter-standorte-oev.oereb_20190724.xtf   # XTF-File
- LIEFEREINHEIT =   # Liefereinheit
- LOGFILE =   # Logfile
- OEREB2_DATABASE =   # Oereb2-Database
- OEREB2_USERNAME =   # Oereb2-Username
- OEREB2_PASSWORD =   # Oereb2-Password
- LEGEND_BASEURL =   # Legenden-Basis-URL
- LEGEND_BASEDIR =
- OEREB_PG_DATABASE =
- OEREB_PG_HOST =
- OEREB_PG_PASSWORD =
- OEREB_PG_PORT =
- OEREB_PG_USERNAME =
- SCHEMA =
- OEREB2_CONNECTIONFILE =
- STROKER =
- law_status = inForce

Readers:
- ch.ehi.fme.Main_1: ch.ehi.fme.Main from $(XTF_FILE)

Writers:
- GEODATABASE_SDE_1: GEODATABASE_SDE
- ORACLE_NONSPATIAL_1: ORACLE_NONSPATIAL to $(OEREB2_DATABASE)
- POSTGRES_1: POSTGRES to $(OEREB_PG_DATABASE)
- POSTGRES_2: POSTGRES to $(OEREB_PG_DATABASE)
- POSTGRES_3: POSTGRES to $(OEREB_PG_DATABASE)
- POSTGRES_4: POSTGRES to $(OEREB_PG_DATABASE)
- POSTGRES_5: POSTGRES to $(OEREB_PG_DATABASE)
- POSTGRES_6: POSTGRES to $(OEREB_PG_DATABASE)
- POSTGRES_7: POSTGRES to $(OEREB_PG_DATABASE)
- POSTGRES_8: POSTGRES to $(OEREB_PG_DATABASE)
- POSTGRES_9: POSTGRES to $(OEREB_PG_DATABASE)
- POSTGIS_1: POSTGIS to $(OEREB_PG_DATABASE) in EPSG:2056
- POSTGIS_2: POSTGIS to $(OEREB_PG_DATABASE) in EPSG:2056

Aggregator_2_Aggregate: Logger
    LOG_FEATURE = LOG_ONLY
    MAXCOORDS = 20
    MAXFEATS = 20
    MESSAGE = Feature is:
    SEVERITY = INFO

Bookmark: AMT
Note: OeREBKRMvs_V1_1.Vorschriften.Amt
OeREBKRMvs_V1_1.Vorschriften.Amt (reader ch.ehi.fme.Main_1)
    attributes: xtf_id xtf_char(200), Name{}.xtf_class xtf_char(77), Name{}.LocalisedText{}.xtf_class xtf_char(77), Name{}.LocalisedText{}.Language xtf_char(255), Name{}.LocalisedText{}.Text xtf_buffer, AmtImWeb xtf_char(1023), UID xtf_char(12)
    -> AMT [AttributeCreator_2_INPUT_184]
AMT
    LIEFEREINHEIT = $(LIEFEREINHEIT)
    AttributeRemover_3_OUTPUT_236 -> AttributeKeeper_3
    AttributeRemover_3_OUTPUT_236 -> AMT (writer ORACLE_NONSPATIAL_1)
    AttributeRemover_3_OUTPUT_236 -> AttributeManager_6
AttributeKeeper_3
    KEEP_ATTRS = AMT_LIEFEREINHEIT,AMT_XTF_ID,AMT_OID
    -> FeatureMerger_4 [SUPPLIER]
    -> FeatureMerger_10 [SUPPLIER]
    -> FeatureMerger_3 [SUPPLIER]
Note: OEREB2.AMT
AMT (writer ORACLE_NONSPATIAL_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(6,0), AMT_LINE1 nvarchar(80), AMT_LINE2 nvarchar(80), AMT_STREET nvarchar(100), AMT_NUMBER nvarchar(7), AMT_POSTALCODE nvarchar(4), AMT_CITY nvarchar(60)
AttributeManager_6
    ATTR_TABLE:
      REMOVE AMT_XTF_ID
      RENAME_SET_VALUE AMT_AMTIMWEB_DE > office_at_web
      REMOVE AMT_AMTIMWEB_FR
      REMOVE AMT_NAME_DE
      REMOVE AMT_NAME_FR
      RENAME_SET_VALUE AMT_OID > id
      RENAME_SET_VALUE UID > uid
    -> office (writer POSTGRES_1)
office (writer POSTGRES_1)
    attributes: id varchar(80),PrimaryKey, name json, office_at_web varchar(80), uid varchar(12), line1 varchar(80), line2 varchar(80), street varchar(80), number varchar(80), postal_code int4, city varchar(80), liefereinheit int4

Bookmark: DARSTELLUNSDIENST
Note: OeREBKRMtrsfr_V1_1.Transferstruktur.DarstellungsDienst
OeREBKRMtrsfr_V1_1.Transferstruktur.DarstellungsDienst (reader ch.ehi.fme.Main_1)
    attributes: xtf_id xtf_char(200), VerweisWMS xtf_char(1023), LegendeImWeb xtf_char(1023), Legende{}.xtf_class xtf_char(77), Legende{}.Symbol xtf_buffer, Legende{}.LegendeText{}.xtf_class xtf_char(77), Legende{}.LegendeText{}.LocalisedText{}.xtf_class xtf_char(77), Legende{}.LegendeText{}.LocalisedText{}.Language xtf_char(255), Legende{}.LegendeText{}.LocalisedText{}.Text xtf_buffer, Legende{}.ArtCode xtf_char(40), Legende{}.ArtCodeliste xtf_char(1023), Legende{}.Thema xtf_char(255), Legende{}.SubThema xtf_char(60), Legende{}.WeiteresThema xtf_char(120)
    -> DARSTELLUNSDIENST [UUIDGenerator_INPUT_349]
DARSTELLUNSDIENST
    LEGEND_BASEURL = $(LEGEND_BASEURL)
    LIEFEREINHEIT = $(LIEFEREINHEIT)
    AttributeCopier_OUTPUT_233 -> AttributeKeeper_2
    AttributeCopier_OUTPUT_233 -> DARSTELLUNGSDIENST (writer ORACLE_NONSPATIAL_1)
    AttributeCopier_OUTPUT_233 -> AttributeManager_5
    AttributeCopier_OUTPUT_233 -> AttributeKeeper_6
Note: OEREB2.DARSTELLUNGSDIENST
DARSTELLUNGSDIENST (writer ORACLE_NONSPATIAL_1)
    attributes: DAR_OID nvarchar(128), DAR_XTF_ID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(6,0)
AttributeManager_5
    ATTR_TABLE:
      REMOVE DAR_XTF_ID
      RENAME_SET_VALUE DAR_VERWEISWMS_DE > reference_wms
      REMOVE DAR_VERWEISWMS_FR
      RENAME_SET_VALUE DAR_OID > id
      RENAME_SET_VALUE DAR_LEGENDEIMWEB_DE > lege
    -> view_service (writer POSTGRES_2)
view_service (writer POSTGRES_2)
    attributes: id varchar(80),PrimaryKey, reference_wms varchar(80), legend_at_web json, liefereinheit int4

Bookmark: LEGENDENBILDLI
  In den Feldern symbol und symbol_url werden weiterhin die vom AGI erstellten Bilder referenziert bzw. importiert. Grund: die vom Bund gelieferten Bilder sind rechteckig (gemäss Weisung) und passen nicht in unser quadratisches Schema. Wenn wir auf rechteckige Bilder umsteigen, können wir die Bundesbilder wieder einsetzen. Es hat in den Transferdaten auch nicht in jedem Fall eine LegendeImWeb, die für uns aber sehr wichtig ist.
AttributeKeeper_6
    KEEP_ATTRS = DAR_OID
    KEEP_LIST = Legende{}.ArtCode Legende{}.ArtCodeliste Legende{}.LegendeText{} Legende{}.LegendeText{}.LocalisedText{} Legende{}.LegendeText{}.LocalisedText{}.Language Legende{}.LegendeText{}.LocalisedText{}.Text Legende{}.LegendeText{}.LocalisedText{}.xtf_class Legende{}.LegendeText{}.xtf_class Legende{}.SubThema Legende{}.Symbol Legende{}.Thema Legende{}.WeiteresThema Legende{}.xtf_class
    -> ListExploder
ListExploder
    ATTR_ACCUM_MODE = Merge List Attributes
    ATTR_CONFLICT_RES = Use List Attribute Values
    INDEX_ATTR = _element_index
    LIST_ATTR = Legende{}
    ELEMENTS -> FeatureMerger_11 [REQUESTOR]
    ELEMENTS -> ListExploder_Elements
ListExploder_Elements: Logger
    LOG_FEATURE = LOG_ONLY
    MAXCOORDS = 20
    MAXFEATS = 20
    MESSAGE = Feature is:
    SEVERITY = INFO
AttributeKeeper_7
    KEEP_ATTRS = EIB_ARTCODE,EIB_LEGENDESYMBOL_DE,DAR_OID
    -> Aggregator_2
Aggregator_2
    ACCUM_ATTRS_NAME = Drop Incoming Attributes
    GROUP_BY = EIB_ARTCODE EIB_LEGENDESYMBOL_DE DAR_OID
    MODE = Attributes Only
    ORDERED = No
    SEP = ,
    AGGREGATE -> FeatureMerger_11 [SUPPLIER]
    AGGREGATE -> Aggregator_2_Aggregate
Note: symbol_url gibs nur in den Eigentumsbeschraenkungen. Daher Join nötig.
FeatureMerger_11
    ATTR_ACCUM_MODE = Merge Supplier
    ATTR_CONFLICT_RES = Use Requestor
    IGNORE_NULLS = No
    JOIN_KEYS = @Value(DAR_OID) @Value(DAR_OID) AUTO @Value(ArtCode) @Value(EIB_ARTCODE) AUTO
    MERGE_TYPE = Attributes Only
    PROCESS_DUPS = NO
    REJECT_NULL_MISSING_KEYS = No
    SUPPLIERS_FIRST = No
    MERGED -> LEGEND_ENTRY
LEGEND_ENTRY
    ARTCODE = @Value(ArtCode)
    ARTCODELISTE = @Value(ArtCodeliste)
    DAR_OID = @Value(DAR_OID)
    EIB_ARTCODE = @Value(EIB_ARTCODE)
    EIB_LEGENDESYMBOL_DE = @Value(EIB_LEGENDESYMBOL_DE)
    LIEFEREINHEIT = $(LIEFEREINHEIT)
    SUBTHEMA = @Value(SubThema)
    SYMBOL = @Value(Symbol)
    THEMA = @Value(Thema)
    WEITERESTHEMA = @Value(WeiteresThema)
    XTF_CLASS = @Value(xtf_class)
    -> legend_entry (writer POSTGRES_4)
legend_entry (writer POSTGRES_4)
    attributes: id varchar(80),PrimaryKey, symbol varchar(80), symbol_url varchar(80), legend_text json, type_code varchar(40), type_code_list varchar(80), topic varchar(80), sub_theme json, other_theme varchar(80), view_service_id varchar(80), liefereinheit int4

Bookmark: EIGENTUMSBESCHRAENKUNG
AttributeKeeper_2
    KEEP_ATTRS = DAR_OID,DAR_XTF_ID
    -> FeatureMerger_2 [SUPPLIER]
Note: OeREBKRMtrsfr_V1_1.Transferstruktur.Eigentumsbeschraenkung
OeREBKRMtrsfr_V1_1.Transferstruktur.Eigentumsbeschraenkung (reader ch.ehi.fme.Main_1)
    attributes: xtf_id xtf_char(200), Aussage{}.xtf_class xtf_char(77), Aussage{}.LocalisedText{}.xtf_class xtf_char(77), Aussage{}.LocalisedText{}.Language xtf_char(255), Aussage{}.LocalisedText{}.Text xtf_buffer, Thema xtf_char(255), SubThema xtf_char(60), WeiteresThema xtf_char(120), ArtCode xtf_char(40), ArtCodeliste xtf_char(1023), Rechtsstatus xtf_char(255), publiziertAb xtf_date, DarstellungsDienst xtf_char(200), ZustaendigeStelle xtf_char(200)
    -> EIGENTUMSBESCHRAENKUNG [SQLExecutor_2_INITIATOR_61]
EIGENTUMSBESCHRAENKUNG
    LEGEND_BASEURL = $(LEGEND_BASEURL)
    LIEFEREINHEIT = $(LIEFEREINHEIT)
    OEREB2_DATABASE = $(OEREB2_DATABASE)
    OEREB2_PASSWORD = $(OEREB2_PASSWORD)
    OEREB2_USERNAME = $(OEREB2_USERNAME)
    PythonCaller_OUTPUT_55 -> AttributeKeeper_5
    PythonCaller_OUTPUT_55 -> FeatureMerger_2 [REQUESTOR]
Note: Join mit Darstellungsdienst
FeatureMerger_2
    ATTR_ACCUM_MODE = Merge Supplier
    ATTR_CONFLICT_RES = Use Requestor
    IGNORE_NULLS = No
    JOIN_KEYS = @Value(DarstellungsDienst) @Value(DAR_XTF_ID) AUTO
    MERGE_TYPE = Attributes Only
    PROCESS_DUPS = NO
    REJECT_NULL_MISSING_KEYS = No
    SUPPLIERS_FIRST = No
    MERGED -> FeatureMerger_10 [REQUESTOR]
    MERGED -> AttributeKeeper_7
Note: Join mit Amt
FeatureMerger_10
    ATTR_ACCUM_MODE = Merge Supplier
    ATTR_CONFLICT_RES = Use Requestor
    IGNORE_NULLS = Yes
    JOIN_KEYS = @Value(ZustaendigeStelle) @Value(AMT_XTF_ID) AUTO
    MERGE_TYPE = Attributes Only
    PROCESS_DUPS = NO
    REJECT_NULL_MISSING_KEYS = No
    SUPPLIERS_FIRST = No
    MERGED -> AttributeRemover_4
AttributeRemover_4
    REMOVE_ATTRS = AMT_LIEFEREINHEIT,AMT_XTF_ID,DarstellungsDienst,SubThema,ZustaendigeStelle,DAR_XTF_ID,WeiteresThema
    -> AttributeKeeper
    -> Counter
    -> AttributeManager_3
Counter
    CNT_ATTR = EIB_SORT
    DOMAIN = counter
    SCOPE = Global
    START = 1
    -> EIGENTUMSBESCHRAENKUNG (writer ORACLE_NONSPATIAL_1)
Note: OEREB2.EIGENTUMSBESCHRAENKUNG
EIGENTUMSBESCHRAENKUNG (writer ORACLE_NONSPATIAL_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), STH_ID number(10,0), EIB_SORT number(10,0), EIB_LEGENDESYMBOL_DE nvarchar(1023), EIB_LEGENDESYMBOL_FR nvarchar(1023)
AttributeManager_3
    ATTR_TABLE:
      REMOVE EIB_XTF_ID
      RENAME_SET_VALUE EIB_ARTCODE > type_code
      RENAME_SET_VALUE EIB_ARTCODELISTE > type_code_list
      RENAME_SET_VALUE EIB_PUBLIZIERTAB > published_from
      RENAME_SET_VALUE EIB_OID > id
      RENAME_SET_VALUE DAR_OID > view_service_id
      RENAME_SET_VALUE AMT_OID > office_id
    -> public_law_restriction (writer POSTGRES_3)
public_law_restriction (writer POSTGRES_3)
    attributes: id varchar(80),PrimaryKey, information json, topic varchar(80), sub_theme json, other_theme varchar(80), type_code varchar(40), type_code_list varchar(80), law_status varchar(80), published_from date, view_service_id varchar(80), office_id varchar(80), liefereinheit int4

Bookmark: ARTIKEL
Note: OeREBKRMvs_V1_1.Vorschriften.Artikel
OeREBKRMvs_V1_1.Vorschriften.Artikel (reader ch.ehi.fme.Main_1)
    attributes: xtf_id xtf_char(200), TextImWeb{}.xtf_class xtf_char(77), TextImWeb{}.LocalisedText{}.xtf_class xtf_char(77), TextImWeb{}.LocalisedText{}.Language xtf_char(255), TextImWeb{}.LocalisedText{}.Text xtf_char(1023), Rechtsstatus xtf_char(255), publiziertAb xtf_date, Nr xtf_char(20), Text{}.xtf_class xtf_char(77), Text{}.LocalisedText{}.xtf_class xtf_char(77), Text{}.LocalisedText{}.Language xtf_char(255), Text{}.LocalisedText{}.Text xtf_buffer, Dokument xtf_char(200)
    -> ARTIKEL [SQLExecutor_8_INITIATOR_245]
ARTIKEL
    LIEFEREINHEIT = $(LIEFEREINHEIT)
    PythonCaller_4_OUTPUT_255 -> ARTIKEL (writer ORACLE_NONSPATIAL_1)
    PythonCaller_4_OUTPUT_255 -> FeatureMerger_6 [REQUESTOR]
Note: OEREB2.ARTIKEL
ARTIKEL (writer ORACLE_NONSPATIAL_1)
    attributes: ART_OID nvarchar(128), ART_XTF_ID nvarchar(128), ART_TEXTIMWEB_DE nvarchar(1023), ART_TEXTIMWEB_FR nvarchar(1023), ART_PUBLIZIERTAB date, ART_NR nvarchar(20), ART_TEXT_DE nclob, ART_TEXT_FR nclob, ART_LIEFEREINHEIT number(6,0), RES_ID number(10,0)
FeatureMerger_6
    ATTR_ACCUM_MODE = Merge Supplier
    ATTR_CONFLICT_RES = Use Requestor
    IGNORE_NULLS = No
    JOIN_KEYS = @Value(Dokument) @Value(VOR_XTF_ID) AUTO
    MERGE_TYPE = Attributes Only
    PROCESS_DUPS = NO
    REJECT_NULL_MISSING_KEYS = No
    SUPPLIERS_FIRST = No
    MERGED -> AttributeManager_8
AttributeManager_8
    ATTR_TABLE:
      REMOVE ART_XTF_ID
      REMOVE ART_PUBLIZIERTAB
      RENAME_SET_VALUE ART_NR > number
      REMOVE RES_ID
      REMOVE ART_TEXT_DE
      REMOVE ART_TEXT_FR
      REMOVE ART_TEXTIMWEB_DE
      REMOVE ART_TEXTIMWEB_FR
      RENAME_SET_VALUE ART_OID > id
      REMOVE VOR_XTF_ID
      RENAME_SET_VALUE VOR_OID > document_id
    -> article (writer POSTGRES_7)
article (writer POSTGRES_7)
    attributes: number varchar(80), text json, id varchar(80),PrimaryKey, document_id varchar(80), liefereinheit int4

Bookmark: GEOMETRIE
AttributeKeeper_5
    KEEP_ATTRS = EIB_XTF_ID,EIB_OID
    -> FeatureMerger [SUPPLIER]
Note: OeREBKRMtrsfr_V1_1.Transferstruktur.Geometrie
OeREBKRMtrsfr_V1_1.Transferstruktur.Geometrie (reader ch.ehi.fme.Main_1)
    attributes: xtf_id xtf_char(200), Punkt_LV95 xtf_buffer, Linie_LV03 xtf_buffer, Linie_LV95 xtf_buffer, Flaeche_LV03 xtf_buffer, Flaeche_LV95 xtf_buffer, Rechtsstatus xtf_char(255), publiziertAb xtf_date, MetadatenGeobasisdaten xtf_char(1023), Eigentumsbeschraenkung xtf_char(200), ZustaendigeStelle xtf_char(200)
    -> GEOMETRIE [DateFormatter_2_INPUT_99]
GEOMETRIE
    LIEFEREINHEIT = $(LIEFEREINHEIT)
    UUIDGenerator_2_OUTPUT_323 -> FeatureMerger [REQUESTOR]
FeatureMerger
    ATTR_ACCUM_MODE = Merge Supplier
    ATTR_CONFLICT_RES = Use Requestor
    IGNORE_NULLS = No
    JOIN_KEYS = @Value(Eigentumsbeschraenkung) @Value(EIB_XTF_ID) AUTO
    MERGE_TYPE = Attributes Only
    PROCESS_DUPS = NO
    REJECT_NULL_MISSING_KEYS = No
    SUPPLIERS_FIRST = No
    MERGED -> FeatureMerger_3 [REQUESTOR]
FeatureMerger_3
    ATTR_ACCUM_MODE = Merge Supplier
    ATTR_CONFLICT_RES = Use Requestor
    IGNORE_NULLS = Yes
    JOIN_KEYS = @Value(ZustaendigeStelle) @Value(AMT_XTF_ID) AUTO
    MERGE_TYPE = Attributes Only
    PROCESS_DUPS = NO
    REJECT_NULL_MISSING_KEYS = No
    SUPPLIERS_FIRST = No
    MERGED -> AttributeRemover_6
AttributeRemover_6
    REMOVE_ATTRS = Eigentumsbeschraenkung,ZustaendigeStelle,EIB_XTF_ID,AMT_XTF_ID
    -> TestFilter
Note: Geometrie filtern
TestFilter
    DEFAULT_VALUE = UNFILTERED
    TEST_LIST = BOOL_OP,OR,COMPOSITE_TEST,<Unused>,TEST_CLAUSE,"TEST ""@Value(Flaeche_LV95)"" ATTRIBUTE_HAS_VALUE """"",FLAECHE,BOOL_OP,OR,COMPOSITE_TEST,<Unused>,TEST_CLAUSE,"TEST ""@Value(Linie_LV95)"" ATTRIBUTE_HAS_VALUE """"",LINIE,BOOL_OP,OR,COMPOSITE_TEST,<Unused>,TEST_CLAUSE,"TEST ""@Value(Punkt_LV95)"" ATTRIBUTE_HAS_VALUE """"",PUNKT
    FLAECHE -> GeometryReplacer_3
    LINIE -> GeometryReplacer
    PUNKT -> GeometryReplacer_2
    UNFILTERED -> Terminator
GeometryReplacer_2
    KIND_LONG = FME Binary
    REMOVE_ATTRIBUTE = Yes
    SOURCE = @Value(Punkt_LV95)
    -> BulkAttributeRenamer_4
    -> AttributeManager_4
BulkAttributeRenamer_4
    ATTRCHOICE = Selected Attributes
    ATTRLIST = METAGEO_DE METAGEO_FR XTF_ID PUBLIZIERTAB OID
    MODE_CHOICE = RENAME
    PATTERN_ACTION_DISP = ADDPREFIX
    REPLACE_STR = PUN_
    -> PUNKT (writer GEODATABASE_SDE_1)
PUNKT (writer GEODATABASE_SDE_1)
    attributes: PUN_OID char(128), PUN_XTF_ID char(128), PUN_PUBLIZIERTAB date, PUN_METAGEO_DE char(1023), PUN_METAGEO_FR char(1023), PUN_LIEFEREINHEIT integer, EIB_OID char(128), AMT_OID char(128), RES_ID integer
GeometryReplacer_3
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = No
    SOURCE = @Value(Flaeche_LV95)
    SRS_AXIS_ORDER_DISPLAY = Automatic
    -> BulkAttributeRenamer_5
    -> ArcStroker
BulkAttributeRenamer_5
    ATTRCHOICE = Selected Attributes
    ATTRLIST = METAGEO_DE METAGEO_FR XTF_ID PUBLIZIERTAB OID
    MODE_CHOICE = RENAME
    PATTERN_ACTION_DISP = ADDPREFIX
    REPLACE_STR = FLA_
    -> FLAECHE (writer GEODATABASE_SDE_1)
FLAECHE (writer GEODATABASE_SDE_1)
    attributes: FLA_OID char(128), FLA_XTF_ID char(128), FLA_PUBLIZIERTAB date, FLA_METAGEO_DE char(1023), FLA_METAGEO_FR char(1023), FLA_LIEFEREINHEIT integer, EIB_OID char(128), AMT_OID char(128), RES_ID integer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = No
    SOURCE = @Value(Linie_LV95)
    SRS_AXIS_ORDER_DISPLAY = Automatic
    -> BulkAttributeRenamer_3
    -> ArcStroker
ArcStroker
    MAKE_POLY = No
    NUM = $(STROKER)
    STROKE_CHOICE = Number of Interpolated Edges
    TOLERANCE_VAL = 0.0
    STROKED -> GeometryRefiner
GeometryRefiner
    -> AttributeManager_4
AttributeManager_4
    ATTR_TABLE:
      REMOVE XTF_ID
      REMOVE Linie_LV95
      REMOVE Flaeche_LV95
      RENAME_SET_VALUE PUBLIZIERTAB > published_from
      RENAME_SET_VALUE METAGEO_DE > geo_metadata
      REMOVE METAGEO_FR
      REMOVE RES_ID
      REMOVE fme_type
      RENAME_SET_VALUE OID > id
      RENAME_SET_VALUE EIB_OID > public_law_restriction_id
      RENAME_SET_VALUE AMT_OID > office_id
      REMOVE Punkt_LV95
      SET_TO schema = $(SCHEMA)
    -> AttributeFilter
Note: Je nach Schema ist ein anderer Geometrietyp in der Zieltabelle nötig und damit auch ein zusätzlicher FeatureType.
AttributeFilter
    ATTR_NAME = schema
    ATTR_VALUES = airports_project_planning_zones,airports_security_zone_plans,motorways_building_lines,contaminated_public_transport_sites,contaminated_civil_aviation_sites,<Empty>,<Missing>,<Null>,<Unfiltered>
    contaminated_public_transport_sites -> geometry (writer POSTGIS_2)
    contaminated_civil_aviation_sites -> geometry (writer POSTGIS_2)
    airports_project_planning_zones -> geometry (writer POSTGIS_1)
    airports_security_zone_plans -> Aggregator
    motorways_building_lines -> geometry (writer POSTGIS_1)
geometry (writer POSTGIS_1)
    attributes: id varchar(80),PrimaryKey, law_status varchar(80), published_from date, geo_metadata varchar(80), public_law_restriction_id varchar(80), office_id varchar(80), liefereinheit int4
Note: Homogenous Aggregate: MultiPolygon
Aggregator
    ACCUM_ATTRS_NAME = Use Attributes From One Feature
    AGGREGATE_TYPE = Homogeneous Collection (If Possible)
    GROUP_BY = id
    MODE = Geometry - Assemble One Level
    ORDERED = No
    SEP = ,
    AGGREGATE -> geometry (writer POSTGIS_1)
geometry (writer POSTGIS_1)
    attributes: id varchar(80),PrimaryKey, law_status varchar(80), published_from date, geo_metadata varchar(80), public_law_restriction_id varchar(80), office_id varchar(80), liefereinheit int4
geometry (writer POSTGIS_1)
    attributes: id varchar(80),PrimaryKey, law_status varchar(80), published_from date, geo_metadata varchar(80), public_law_restriction_id varchar(80), office_id varchar(80), liefereinheit int4
Note: Beide KBS sind GeometryCollection, daher reicht ein einziger FeatureType.
geometry (writer POSTGIS_2)
    attributes: id varchar(80), law_status varchar(80), published_from date, geo_metadata varchar(80), public_law_restriction_id varchar(80), office_id varchar(80), liefereinheit int4
BulkAttributeRenamer_3
    ATTRCHOICE = Selected Attributes
    ATTRLIST = METAGEO_DE METAGEO_FR XTF_ID PUBLIZIERTAB OID
    MODE_CHOICE = RENAME
    PATTERN_ACTION_DISP = ADDPREFIX
    REPLACE_STR = LIN_
    -> LINIE (writer GEODATABASE_SDE_1)
LINIE (writer GEODATABASE_SDE_1)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
Terminator
    MESSAGE = Objekt hat keine gültige Geometrie!!!

Bookmark: HINWEISVORSCHRIFT
AttributeKeeper
    KEEP_ATTRS = EIB_XTF_ID,EIB_OID
    -> FeatureMerger_5 [SUPPLIER]
OeREBKRMtrsfr_V1_1.Transferstruktur.HinweisVorschrift (reader ch.ehi.fme.Main_1)
    attributes: xtf_id xtf_char(200), Eigentumsbeschraenkung xtf_char(200), Vorschrift xtf_char(200), ArtikelNr{}.xtf_class xtf_char(77), ArtikelNr{}.value xtf_char(20)
    -> HINWEISVORSCHRIFT [HINWEISVORSCHRIFT_UUIDGenerator_INPUT_220]
HINWEISVORSCHRIFT
    LIEFEREINHEIT = $(LIEFEREINHEIT)
    HINWEISVORSCHRIFT_AttributeRenamer_OUTPUT_212 -> FeatureMerger_5 [REQUESTOR]
Note: Join mit Eigentums- / beschränkung
FeatureMerger_5
    ATTR_ACCUM_MODE = Merge Supplier
    ATTR_CONFLICT_RES = Use Requestor
    IGNORE_NULLS = No
    JOIN_KEYS = @Value(Eigentumsbeschraenkung) @Value(EIB_XTF_ID) AUTO
    MERGE_TYPE = Attributes Only
    PROCESS_DUPS = NO
    REJECT_NULL_MISSING_KEYS = No
    SUPPLIERS_FIRST = No
    MERGED -> FeatureMerger_7 [REQUESTOR]
Note: Join mit Vorschrift
FeatureMerger_7
    ATTR_ACCUM_MODE = Merge Supplier
    ATTR_CONFLICT_RES = Use Requestor
    IGNORE_NULLS = No
    JOIN_KEYS = @Value(Vorschrift) @Value(VOR_XTF_ID) AUTO
    MERGE_TYPE = Attributes Only
    PROCESS_DUPS = NO
    REJECT_NULL_MISSING_KEYS = No
    SUPPLIERS_FIRST = No
    MERGED -> HINVOR (writer ORACLE_NONSPATIAL_1)
    MERGED -> AttributeManager_2
Note: OEREB2.HINVOR
HINVOR (writer ORACLE_NONSPATIAL_1)
    attributes: HIV_ID nvarchar(128), HIV_XTF_ID nvarchar(128), HIV_ARTNR nvarchar(255), HIV_LIEFEREINHEIT number(6,0), EIB_OID nvarchar(128), VOR_OID nvarchar(128)
AttributeManager_2
    ATTR_TABLE:
      REMOVE HIV_XTF_ID
      REMOVE Eigentumsbeschraenkung
      REMOVE Vorschrift
      RENAME_SET_VALUE HIV_ID > id
      RENAME_SET_VALUE HIV_ARTNR > article_numbers
      REMOVE EIB_XTF_ID
      RENAME_SET_VALUE EIB_OID > public_law_restriction_id
      REMOVE VOR_XTF_ID
      RENAME_SET_VALUE VOR_OID > document_id
    -> public_law_restriction_document (writer POSTGRES_9)
public_law_restriction_document (writer POSTGRES_9)
    attributes: id varchar(80),PrimaryKey, public_law_restriction_id varchar(80), document_id varchar(80), article_numbers varchar(80), liefereinheit int4

Bookmark: VORSCHRIFT
Note: OeREBKRMvs_V1_1.Vorschriften.Rechtsvorschrift
OeREBKRMvs_V1_1.Vorschriften.Rechtsvorschrift (reader ch.ehi.fme.Main_1)
    attributes: xtf_id xtf_char(200), TextImWeb{}.xtf_class xtf_char(77), TextImWeb{}.LocalisedText{}.xtf_class xtf_char(77), TextImWeb{}.LocalisedText{}.Language xtf_char(255), TextImWeb{}.LocalisedText{}.Text xtf_char(1023), Rechtsstatus xtf_char(255), publiziertAb xtf_date, Titel{}.xtf_class xtf_char(77), Titel{}.LocalisedText{}.xtf_class xtf_char(77), Titel{}.LocalisedText{}.Language xtf_char(255), Titel{}.LocalisedText{}.Text xtf_buffer, OffiziellerTitel{}.xtf_class xtf_char(77), OffiziellerTitel{}.LocalisedText{}.xtf_class xtf_char(77), OffiziellerTitel{}.LocalisedText{}.Language xtf_char(255), OffiziellerTitel{}.LocalisedText{}.Text xtf_buffer, Abkuerzung{}.xtf_class xtf_char(77), Abkuerzung{}.LocalisedText{}.xtf_class xtf_char(77), Abkuerzung{}.LocalisedText{}.Language xtf_char(255), Abkuerzung{}.LocalisedText{}.Text xtf_buffer, OffizielleNr xtf_char(20), Kanton xtf_char(255), Gemeinde xtf_int32, Dokument xtf_buffer, ZustaendigeStelle xtf_char(200)
    -> RECHTSVORSCHRIFT [AttributeCreator_3_INPUT_192]
Note: OeREBKRMvs_V1_1.Vorschriften.Dokument
OeREBKRMvs_V1_1.Vorschriften.Dokument (reader ch.ehi.fme.Main_1)
    attributes: xtf_id xtf_char(200), TextImWeb{}.xtf_class xtf_char(77), TextImWeb{}.LocalisedText{}.xtf_class xtf_char(77), TextImWeb{}.LocalisedText{}.Language xtf_char(255), TextImWeb{}.LocalisedText{}.Text xtf_char(1023), Rechtsstatus xtf_char(255), publiziertAb xtf_date, Titel{}.xtf_class xtf_char(77), Titel{}.LocalisedText{}.xtf_class xtf_char(77), Titel{}.LocalisedText{}.Language xtf_char(255), Titel{}.LocalisedText{}.Text xtf_buffer, OffiziellerTitel{}.xtf_class xtf_char(77), OffiziellerTitel{}.LocalisedText{}.xtf_class xtf_char(77), OffiziellerTitel{}.LocalisedText{}.Language xtf_char(255), OffiziellerTitel{}.LocalisedText{}.Text xtf_buffer, Abkuerzung{}.xtf_class xtf_char(77), Abkuerzung{}.LocalisedText{}.xtf_class xtf_char(77), Abkuerzung{}.LocalisedText{}.Language xtf_char(255), Abkuerzung{}.LocalisedText{}.Text xtf_buffer, OffizielleNr xtf_char(20), Kanton xtf_char(255), Gemeinde xtf_int32, Dokument xtf_buffer, ZustaendigeStelle xtf_char(200)
    -> RECHTSVORSCHRIFT [AttributeCreator_3_INPUT_192]
RECHTSVORSCHRIFT
    LIEFEREINHEIT = $(LIEFEREINHEIT)
    SQLExecutor_7_RESULT_196 -> FeatureMerger_4 [REQUESTOR]
FeatureMerger_4
    ATTR_ACCUM_MODE = Merge Supplier
    ATTR_CONFLICT_RES = Use Requestor
    IGNORE_NULLS = Yes
    JOIN_KEYS = @Value(ZustaendigeStelle) @Value(AMT_XTF_ID) AUTO
    MERGE_TYPE = Attributes Only
    PROCESS_DUPS = NO
    REJECT_NULL_MISSING_KEYS = No
    SUPPLIERS_FIRST = No
    MERGED -> AttributeKeeper_4
    MERGED -> VORSCHRIFT (writer ORACLE_NONSPATIAL_1)
    MERGED -> AttributeManager_7
Note: OEREB2.VORSCHRIFT
VORSCHRIFT (writer ORACLE_NONSPATIAL_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128)
AttributeManager_7
    ATTR_TABLE:
      REMOVE VOR_XTF_ID
      RENAME_SET_VALUE VOR_PUBLIZIERTAB > published_from
      RENAME_SET_VALUE VOR_OFFIZIELLENR > official_number
      RENAME_SET_VALUE VOR_KANTON > canton
      RENAME_SET_VALUE BFS_NR > municipality
      RENAME_SET_VALUE VOR_DOKUMENT > file
      REMOVE ZustaendigeStelle
      REMOVE VOR_TITEL_DE
      REMOVE VOR_TITEL_FR
      REMOVE VOR_OFFIZIELLERTITEL_DE
      REMOVE VOR_OFFIZIELLERTITEL_FR
      REMOVE VOR_ABKUERZUNG_DE
      REMOVE VOR_ABKUERZUNG_FR
      REMOVE VOR_TEXTIMWEB_DE
      REMOVE VOR_TEXTIMWEB_FR
      RENAME_SET_VALUE RES_ID > reference_wms
      RENAME_SET_VALUE VOR_OID > id
      REMOVE AMT_XTF_ID
      RENAME_SET_VALUE AMT_OID > office_id
      SET_TO type = document
    -> document (writer POSTGRES_6)
    -> document_base (writer POSTGRES_5)
document (writer POSTGRES_6)
    attributes: document_type varchar(80), title json, official_title json, abbreviation json, official_number varchar(80), canton varchar(2), municipality int4, file varchar(80), id varchar(80),PrimaryKey, office_id varchar(80), liefereinheit int4
document_base (writer POSTGRES_5)
    attributes: id varchar(80),PrimaryKey, text_at_web json, law_status varchar(80), published_from date, type varchar(80), liefereinheit int4
AttributeKeeper_4
    KEEP_ATTRS = VOR_XTF_ID,VOR_OID
    -> FeatureMerger_8 [SUPPLIER]
    -> FeatureMerger_7 [SUPPLIER]
    -> FeatureMerger_9 [SUPPLIER]
    -> FeatureMerger_6 [SUPPLIER]

Bookmark: HINWEIDOK
Note: OeREBKRMvs_V1_1.Vorschriften.HinweisWeitereDokumente
OeREBKRMvs_V1_1.Vorschriften.HinweisWeitereDokumente (reader ch.ehi.fme.Main_1)
    attributes: xtf_id xtf_char(200), Ursprung xtf_char(200), Hinweis xtf_char(200), ArtikelNr{}.xtf_class xtf_char(77), ArtikelNr{}.value xtf_char(20)
    -> HINWEIDOK [UUIDGenerator_INPUT_184]
HINWEIDOK
    LIEFEREINHEIT = $(LIEFEREINHEIT)
    UUIDGenerator_OUTPUT_184 -> FeatureMerger_9 [REQUESTOR]
Note: Ursprung joinen
FeatureMerger_9
    ATTR_ACCUM_MODE = Merge Supplier
    ATTR_CONFLICT_RES = Use Requestor
    IGNORE_NULLS = Yes
    JOIN_KEYS = @Value(Ursprung) @Value(VOR_XTF_ID) AUTO
    MERGE_TYPE = Attributes Only
    PROCESS_DUPS = NO
    REJECT_NULL_MISSING_KEYS = No
    SUPPLIERS_FIRST = No
    MERGED -> AttributeRenamer
AttributeRenamer
    ATTR_TABLE = RENAME_SET_DEFAULT VOR_OID > VOR_OIDURSPRUNG
    -> AttributeRemover_11
AttributeRemover_11
    REMOVE_ATTRS = Ursprung,VOR_XTF_ID
    -> FeatureMerger_8 [REQUESTOR]
Note: Hinweis joinen. Hinweise (gesetzliche Grundlagen) / können auch ausserhalb des ITFs liegen). Deshalb / muss auch der NOT_MERGED-Ausgang bearbeitet werden.
FeatureMerger_8
    ATTR_ACCUM_MODE = Merge Supplier
    ATTR_CONFLICT_RES = Use Requestor
    IGNORE_NULLS = Yes
    JOIN_KEYS = @Value(Hinweis) @Value(VOR_XTF_ID) AUTO
    MERGE_TYPE = Attributes Only
    PROCESS_DUPS = NO
    REJECT_NULL_MISSING_KEYS = No
    SUPPLIERS_FIRST = No
    MERGED -> AttributeRenamer_2
    UNMERGED_REQUESTOR -> AttributeRenamer_3
AttributeRenamer_2
    ATTR_TABLE = RENAME_SET_DEFAULT VOR_OID > VOR_OIDHINWEIS
    -> AttributeRemover_12
AttributeRemover_12
    REMOVE_ATTRS = Hinweis,VOR_XTF_ID
    -> HINWEIDOK (writer ORACLE_NONSPATIAL_1)
    -> AttributeManager
AttributeRenamer_3
    ATTR_TABLE = RENAME_SET_DEFAULT Hinweis > VOR_OIDHINWEIS
    -> HINWEIDOK (writer ORACLE_NONSPATIAL_1)
    -> AttributeManager
AttributeManager
    ATTR_TABLE:
      REMOVE HWD_XTF_ID
      RENAME_SET_VALUE VOR_OIDHINWEIS > reference_document_id
      RENAME_SET_VALUE HWD_ID > id
      RENAME_SET_VALUE HWD_ARTNR > article_numbers
      RENAME_SET_VALUE VOR_OIDURSPRUNG > document_id
    -> document_reference (writer POSTGRES_8)
document_reference (writer POSTGRES_8)
    attributes: id varchar(80),PrimaryKey, document_id varchar(80), reference_document_id varchar(80), article_numbers varchar(80), liefereinheit int4
Note: OEREB2.HINWEIDOK
HINWEIDOK (writer ORACLE_NONSPATIAL_1)
    attributes: HWD_ID nvarchar(128), HWD_XTF_ID nvarchar(128), HWD_LIEFEREINHEIT number(6,0), HWD_ARTNR nvarchar(255), VOR_OIDURSPRUNG nvarchar(128), VOR_OIDHINWEIS nvarchar(128)

Bookmark: Nicht verwendete Klassen des Rahmenmodells
Note: OeREBKRMtrsfr_V1_1.Transferstruktur.HinweisDefinitionDokument
OeREBKRMtrsfr_V1_1.Transferstruktur.HinweisDefinitionDokument (reader ch.ehi.fme.Main_1) [off]
    attributes: xtf_id xtf_char(200), HinweisDefinition xtf_char(200), Dokument xtf_char(200)
Note: OeREBKRMtrsfr_V1_1.Transferstruktur.HinweisDefinition
OeREBKRMtrsfr_V1_1.Transferstruktur.HinweisDefinition (reader ch.ehi.fme.Main_1) [off]
    attributes: xtf_id xtf_char(200), Thema xtf_char(255), Kanton xtf_char(255), Gemeinde xtf_int32, ZustaendigeStelle xtf_char(200)
Note: OeREBKRMtrsfr_V1_1.Transferstruktur.GrundlageVerfeinerung
OeREBKRMtrsfr_V1_1.Transferstruktur.GrundlageVerfeinerung (reader ch.ehi.fme.Main_1) [off]
    attributes: xtf_id xtf_char(200), Grundlage xtf_char(200), Verfeinerung xtf_char(200)
Note: Dictionaries_V1.Dictionaries.Dictionary:
Dictionaries_V1.Dictionaries.Dictionary (reader ch.ehi.fme.Main_1) [off]
    attributes: xtf_id xtf_char(200), Language xtf_char(255), Entries{}.xtf_class xtf_char(77), Entries{}.Text xtf_buffer, Entries{}.Code xtf_char(255)
Note: DictionariesCH_V1.Dictionaries.Dictionary:
DictionariesCH_V1.Dictionaries.Dictionary (reader ch.ehi.fme.Main_1) [off]
    attributes: xtf_id xtf_char(200), Language xtf_char(255), Entries{}.xtf_class xtf_char(77), Entries{}.Text xtf_buffer, Entries{}.Code xtf_char(255)
Note: OeREBKRM_V1_1.CodelistenText.RechtsStatusTxt
OeREBKRM_V1_1.CodelistenText.RechtsStatusTxt (reader ch.ehi.fme.Main_1) [off]
    attributes: xtf_id xtf_char(200), Code xtf_char(255), Titel{}.xtf_class xtf_char(77), Titel{}.LocalisedText{}.xtf_class xtf_char(77), Titel{}.LocalisedText{}.Language xtf_char(255), Titel{}.LocalisedText{}.Text xtf_buffer
Note: OeREBKRM_V1_1.CodelistenText.ThemaTxt
OeREBKRM_V1_1.CodelistenText.ThemaTxt (reader ch.ehi.fme.Main_1) [off]
    attributes: xtf_id xtf_char(200), Code xtf_char(255), Titel{}.xtf_class xtf_char(77), Titel{}.LocalisedText{}.xtf_class xtf_char(77), Titel{}.LocalisedText{}.Language xtf_char(255), Titel{}.LocalisedText{}.Text xtf_buffer

FME custom transformer RECHTSVORSCHRIFT

Parameters:
- LIEFEREINHEIT =   # Liefereinheit

AttributeCreator_3_INPUT_192 (input)
    -> AttributeCreator_3
Note: Mehrsprachige Felder / deklarieren
AttributeCreator_3
    ATTR_TABLE = SET_TO multilangfields = Titel,Abkuerzung,OffiziellerTitel,TextImWeb
    -> PythonCaller_3
Note: Mehrsprachiger Text / verarbeiten
PythonCaller_3
    NEW_ATTRIBUTES = Titel_DE Titel_FR OffiziellerTitel_DE OffiziellerTitel_FR Abkuerzung_DE Abkuerzung_FR TextImWeb_DE TextImWeb_FR
    PYTHONSYMBOL = processMultilangFields
    -> AttributeValueMapper_2
Note: law_status mappen
AttributeValueMapper_2
    DIRECTION = Forward (Source To Destination)
    LUT = inKraft,inForce,laufendeAenderung,runningModification
    SRC = Rechtsstatus
    VAL_ATTR = law_status
    -> AttributeValueMapper_3
Note: RES_ID mappen
AttributeValueMapper_3
    DIRECTION = Forward (Source To Destination)
    LUT = inKraft,1,laufendeAenderung,2
    SRC = Rechtsstatus
    VAL_ATTR = RES_ID
    -> DateFormatter_3
Note: publiziertAb / formatieren
DateFormatter_3
    DATE_ATTR = publiziertAb
    FMT = FME Date (%Y%m%d)
    INVALID_DATE_VALUE = _FME_NO_OP_
    SRCFMT = Unknown - Automatic Detection
    -> AttributeValueMapper
Note: Vorschriftsart setzen / (REVO oder HINW) je / nach FeatureType
AttributeValueMapper
    DEFAULT_VALUE = -99
    DIRECTION = Forward (Source To Destination)
    LUT = OeREBKRMvs_V1_1.Vorschriften.Dokument,3,OeREBKRMvs_V1_1.Vorschriften.Rechtsvorschrift,1
    SRC = fme_feature_type
    VAL_ATTR = VOA_ID
    -> UUIDGenerator
UUIDGenerator
    UUID_ATTR = VOR_OID
    -> AttributeRenamer
AttributeRenamer
    ATTR_TABLE:
      RENAME_SET_DEFAULT xtf_id > VOR_XTF_ID
      RENAME_SET_DEFAULT TextImWeb_DE > VOR_TEXTIMWEB_DE
      RENAME_SET_DEFAULT publiziertAb > VOR_PUBLIZIERTAB
      RENAME_SET_DEFAULT Titel_DE > VOR_TITEL_DE
      RENAME_SET_DEFAULT Titel_FR > VOR_TITEL_FR
      RENAME_SET_DEFAULT OffiziellerTitel_DE > VOR_OFFIZIELLERTITEL_DE
      RENAME_SET_DEFAULT OffiziellerTitel_FR > VOR_OFFIZIELLERTITEL_FR
      RENAME_SET_DEFAULT Abkuerzung_DE > VOR_ABKUERZUNG_DE
      RENAME_SET_DEFAULT Abkuerzung_FR > VOR_ABKUERZUNG_FR
      RENAME_SET_DEFAULT OffizielleNr > VOR_OFFIZIELLENR
      RENAME_SET_DEFAULT Dokument > VOR_DOKUMENT
      RENAME_SET_DEFAULT Kanton > VOR_KANTON
      RENAME_SET_DEFAULT Gemeinde > BFS_NR
      RENAME_SET_DEFAULT TextImWeb_FR > VOR_TEXTIMWEB_FR
    -> JSONTemplater_5 [ROOT]
Note: text_at_web-Attribut als JSON-String / aufbauen.
JSONTemplater_5
    RESULT_ATTRIBUTE = text_at_web
    ROOT_QUERY_EXPR:
      {
          "fr": fme:get-attribute("VOR_TEXTIMWEB_FR"),
          "de": fme:get-attribute("VOR_TEXTIMWEB_DE")
      }
    VISIBLE_QUERY_VALIDATE = Yes
    -> JSONTemplater_2 [ROOT]
Note: title-Attribut als JSON-String / aufbauen.
JSONTemplater_2
    RESULT_ATTRIBUTE = title
    ROOT_QUERY_EXPR:
      {
          "fr": fme:get-attribute("VOR_TITEL_FR"),
          "de": fme:get-attribute("VOR_TITEL_DE")
      }
    VISIBLE_QUERY_VALIDATE = Yes
    -> JSONTemplater_3 [ROOT]
Note: official_title-Attribut als JSON-String / aufbauen.
JSONTemplater_3
    RESULT_ATTRIBUTE = official_title
    ROOT_QUERY_EXPR:
      {
          "fr": fme:get-attribute("VOR_OFFIZIELLERTITEL_FR"),
          "de": fme:get-attribute("VOR_OFFIZIELLERTITEL_DE")
      }
    VISIBLE_QUERY_VALIDATE = Yes
    -> JSONTemplater_4 [ROOT]
Note: abbreviation-Attribut als JSON-String / aufbauen.
JSONTemplater_4
    RESULT_ATTRIBUTE = abbreviation
    ROOT_QUERY_EXPR:
      {
          "fr": fme:get-attribute("VOR_ABKUERZUNG_FR"),
          "de": fme:get-attribute("VOR_ABKUERZUNG_DE")
      }
    VISIBLE_QUERY_VALIDATE = Yes
    -> AttributeValueMapper_5
Note: document_type-Attribut / mappen
AttributeValueMapper_5
    DIRECTION = Forward (Source To Destination)
    LUT = 1,LegalProvision,2,Law,3,Hint
    SRC = VOA_ID
    VAL_ATTR = document_type
    -> StringReplacer
Note: #570
StringReplacer
    CASE = NO
    FIND_TEXT = https://map.geo.admin.ch/?
    NO_MATCH = _FME_NO_OP_
    REGEXP = NO
    REPLACE_TEXT = https://map.geo.admin.ch?
    SRC_ATTRS = VOR_TEXTIMWEB_FR,VOR_TEXTIMWEB_DE
    -> AttributeKeeper
AttributeKeeper
    KEEP_ATTRS = VOR_OFFIZIELLENR,text_at_web,VOR_TEXTIMWEB_FR,title,document_type,ZustaendigeStelle,RES_ID,VOR_OFFIZIELLERTITEL_DE,VOR_ABKUERZUNG_DE,VOR_XTF_ID,VOR_TITEL_FR,VOR_KANTON,VOR_LIEFEREINHEIT,BFS_NR,VOR_OID,VOR_PUBLIZIERTAB,VOA_ID,VOR_OFFIZIELLERTITEL_FR,official_title,VOR_DOKUMENT,VOR_TITEL_DE,VOR_ABKUERZUNG_FR,VOR_TEXTIMWEB_DE,abbreviation
    -> SQLExecutor_7_RESULT_196 (output)
SQLExecutor_7_RESULT_196 (output)

FME custom transformer EIGENTUMSBESCHRAENKUNG

Parameters:
- LIEFEREINHEIT =   # Liefereinheit
- OEREB2_DATABASE =   # Oereb2-Database
- OEREB2_USERNAME =   # Oereb2-Username
- OEREB2_PASSWORD =   # Oereb2-Password
- LEGEND_BASEURL =   # Legenden-Basis-URL

Creator
    GEOMTYPE = Geometry Object
    NUM = 1
    CREATED -> FeatureReader [INITIATOR]
Note: THEMA, SUBTHEMA für Lookup
FeatureReader
    ATTRIBUTES = OEREB2.SUBTHEMA,"STH_ID,STH_SUBTHEMA,STH_NAME_DE,STH_NAME_FR,STH_SORT,THE_ID",OEREB2.THEMA,"THE_ID,THE_THEMA,THE_NAME_DE,THE_NAME_FR,THE_GEOIVNR,THE_TYP,THE_SORT,THE_TRANSFERDATE,THE_ISFEDERAL,AMT_OID"
    ATTR_ACCUM_MODE = Only Use Result
    COMBINE_GEOM = Use Result
    DATASET = workt
    FEATURETYPES = OEREB2.SUBTHEMA OEREB2.THEMA
    FORMAT = ORACLE_NONSPATIAL
    ORACLE_NONSPATIAL_CHUNK_SIZE = 200
    ORACLE_NONSPATIAL_PASSWORD =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
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = oereb2
    ORACLE_NONSPATIAL_USE_UNIFIED_DATE_ATTRS = YES
    OUTPUT_FEATURES_DISPLAY = Schema and Data Features
    OEREB2.SUBTHEMA -> AttributeKeeper_3
    OEREB2.THEMA -> AttributeKeeper_2
AttributeKeeper_2
    KEEP_ATTRS = THE_THEMA,THE_ID
    -> FeatureMerger [SUPPLIER]
AttributeKeeper_3
    KEEP_ATTRS = THE_ID,STH_ID
    -> FeatureMerger_2 [SUPPLIER]
SQLExecutor_2_INITIATOR_61 (input)
    -> AttributeValueMapper_2
Note: law_status mappen
AttributeValueMapper_2
    DIRECTION = Forward (Source To Destination)
    LUT = inKraft,inForce,laufendeAenderung,runningModification
    SRC = Rechtsstatus
    VAL_ATTR = law_status
    -> AttributeValueMapper_3
Note: RES_ID mappen
AttributeValueMapper_3
    DIRECTION = Forward (Source To Destination)
    LUT = inKraft,1,laufendeAenderung,2
    SRC = Rechtsstatus
    VAL_ATTR = RES_ID
    -> FeatureMerger [REQUESTOR]
Note: Thema mappen
FeatureMerger
    ATTR_ACCUM_MODE = Merge Supplier
    ATTR_CONFLICT_RES = Use Requestor
    IGNORE_NULLS = No
    JOIN_KEYS = @Value(Thema) @Value(THE_THEMA) AUTO
    MERGE_TYPE = Attributes Only
    PROCESS_DUPS = NO
    REJECT_NULL_MISSING_KEYS = No
    SUPPLIERS_FIRST = No
    MERGED -> FeatureMerger_2 [REQUESTOR]
    UNMERGED_REQUESTOR -> Logger
FeatureMerger_2
    ATTR_ACCUM_MODE = Merge Supplier
    ATTR_CONFLICT_RES = Use Requestor
    IGNORE_NULLS = No
    JOIN_KEYS = @Value(THE_ID) @Value(THE_ID) AUTO
    MERGE_TYPE = Attributes Only
    PROCESS_DUPS = NO
    REJECT_NULL_MISSING_KEYS = No
    SUPPLIERS_FIRST = No
    MERGED -> AttributeValueMapper
    UNMERGED_REQUESTOR -> Logger_2
Note: Topic mappen
AttributeValueMapper
    DIRECTION = Forward (Source To Destination)
    LUT = BaulinienEisenbahnanlagen,RailwaysBuildingLines,BaulinienFlughafenanlagen,AirportsBuildingLines,BaulinienKantonsstrassen,ch.BE.CantonalStreetBuildingLines,BaulinienNationalstrassen,MotorwaysBuildingLines,BelasteteStandorte,ContaminatedSites,BelasteteStandorteMilitaer,ContaminatedMilitarySites,BelasteteStandorteOeffentlicherVerkehr,ContaminatedPublicTransportSites,BelasteteStandorteZivileFlugplaetze,ContaminatedCivilAviationSites,Grundwasserschutzareale,GroundwaterProtectionSites,Grundwasserschutzzonen,GroundwaterProtectionZones,KantonaleNutzungsplanung,ch.BE.CantonalLandUsePlans,KantonaleWaldbaulinien,ch.BE.CantonalForestDistanceLines,Laermempfindlichkeitsstufen,NoiseSensitivityLevels,Nutzungsplanung,LandUsePlans,ProjektierungszonenEisenbahnanlagen,RailwaysProjectPlanningZones,ProjektierungszonenFlughafenanlagen,AirportsProjectPlanningZones,ProjektierungszonenNationalstrassen,MotorwaysProjectPlaningZones,RegionaleNutzungsplanung,ch.BE.RegionalLandUsePlans,RegionaleWaldbaulinien,ch.BE.RegionalForestDistanceLines,SicherheitszonenplanFlughafen,AirportsSecurityZonePlans,Waldabstandslinien,ForestDistanceLines,Waldgrenzen,ForestPerimeters,KantonaleNaturschutzgebiete,ch.BE.CantonalNatureReserves,GeschuetzteGeologischeObjekte,ch.BE.RegionalProtectedGeologicalObjects,GeschuetzteBotanischeObjekte,ch.BE.RegionalProtectedBotanicalObjects
    SRC = Thema
    VAL_ATTR = topic
    -> DateFormatter
Note: publiziertAb / formatieren
DateFormatter
    DATE_ATTR = publiziertAb
    FMT = FME Date (%Y%m%d)
    INVALID_DATE_VALUE = _FME_NO_OP_
    SRCFMT = Unknown - Automatic Detection
    -> UUIDGenerator
Note: Neue UUID generieren
UUIDGenerator
    UUID_ATTR = EIB_OID
    -> AttributeCreator
Note: Mehrsprachige Felder / deklarieren
AttributeCreator
    ATTR_TABLE = SET_TO multilangfields = Aussage
    -> PythonCaller
Note: Mehrsprachiger Text / verarbeiten
PythonCaller
    NEW_ATTRIBUTES = Aussage_DE Aussage_FR
    PYTHONSYMBOL = processMultilangFields
    -> AttributeManager
AttributeManager
    ATTR_TABLE:
      REMOVE multilangfields
      RENAME_SET_VALUE xtf_id > EIB_XTF_ID
      REMOVE Thema
      REMOVE SubThema
      REMOVE WeiteresThema
      RENAME_SET_VALUE ArtCode > EIB_ARTCODE
      RENAME_SET_VALUE ArtCodeliste > EIB_ARTCODELISTE
      REMOVE Rechtsstatus
      RENAME_SET_VALUE publiziertAb > EIB_PUBLIZIERTAB
      RENAME_SET_VALUE Aussage_DE > EIB_AUSSAGE_DE
      RENAME_SET_VALUE Aussage_FR > EIB_AUSSAGE_FR
    -> PythonCaller_2
Note: Legendensymbole bestimmen
PythonCaller_2
    NEW_ATTRIBUTES = EIB_LEGENDESYMBOL_DE EIB_LEGENDESYMBOL_FR
    PYTHONSOURCE:
      # -*- coding: utf-8 -*-
      import fmeobjects

      def processFeature(feature):
          logger = fmeobjects.FMELogFile()
          basisurl = FME_MacroValues['LEGEND_BASEURL']
          artcode = feature.getAttribute("EIB_ARTCODE")

          symbol = ""

          liefereinheit = unicode(FME_MacroValues['LIEFEREINHEIT'])

          if liefereinheit in ("1103", "1108", "1088"):
              symbol = basisurl + liefereinheit + ".png"
          elif liefereinheit in ("1118", "1119"):
              if artcode == 'StatusAltlV1':
                  symbol = basisurl + "f1.png"
              elif artcode == 'StatusAltlV2':
                  symbol = basisurl + "f2.png"
              elif artcode == 'StatusAltlV3':
                  symbol = basisurl + "f3.png"
              elif artcode == 'StatusAltlV4':
                  symbol = basisurl + "f4.png"
              elif artcode == 'StatusAltlV5':
                  symbol = basisurl + "f5.png"
              elif artcode == 'StatusAltlV6':
                  symbol = basisurl + "f6.png"
          else:
              symbol = "es wurde kein Symbol gefunden"
              logger.logMessage("Es wurde keine Symbol-URL gefunden!", fmeobjects.FME_WARN)

          feature.setAttribute("EIB_LEGENDESYMBOL_DE", symbol)
          feature.setAttribute("EIB_LEGENDESYMBOL_FR", symbol)
    PYTHONSYMBOL = processFeature
    -> JSONTemplater_5 [ROOT]
Note: Information-Attribut als JSON-String / aufbauen.
JSONTemplater_5
    RESULT_ATTRIBUTE = information
    ROOT_QUERY_EXPR:
      {
          "fr": fme:get-attribute("EIB_AUSSAGE_FR"),
          "de": fme:get-attribute("EIB_AUSSAGE_DE")
      }
    VISIBLE_QUERY_VALIDATE = Yes
    -> AttributeKeeper
AttributeKeeper
    KEEP_ATTRS = RES_ID,EIB_ARTCODE,EIB_AUSSAGE_DE,DarstellungsDienst,EIB_ARTCODELISTE,EIB_PUBLIZIERTAB,EIB_XTF_ID,STH_ID,EIB_AUSSAGE_FR,EIB_LIEFEREINHEIT,information,EIB_LEGENDESYMBOL_FR,ZustaendigeStelle,EIB_LEGENDESYMBOL_DE,EIB_OID,THE_ID,topic
    -> PythonCaller_OUTPUT_55 (output)
PythonCaller_OUTPUT_55 (output)
Logger_2
    LOG_FEATURE = LOG_ONLY
    MAXCOORDS = 20
    MAXFEATS = 20
    MESSAGE = Feature is:
    SEVERITY = INFO
    LOGGED -> Terminator_2
Terminator_2
    MESSAGE = Kein Subthema
Logger
    LOG_FEATURE = LOG_ONLY
    MAXCOORDS = 20
    MAXFEATS = 20
    MESSAGE = Feature is:
    SEVERITY = INFO
    LOGGED -> Terminator
Terminator
    MESSAGE = Kein Thema

FME custom transformer GEOMETRIE

Parameters:
- LIEFEREINHEIT =   # Liefereinheit

DateFormatter_2_INPUT_99 (input)
    -> DateFormatter_2
Note: publiziertAb / formatieren
DateFormatter_2
    DATE_ATTR = publiziertAb
    FMT = FME Date (%Y%m%d)
    INVALID_DATE_VALUE = _FME_NO_OP_
    SRCFMT = Unknown - Automatic Detection
    -> AttributeExposer
Note: fme_type
AttributeExposer
    ATTR_LIST = fme_type
    -> UUIDGenerator_2
UUIDGenerator_2
    UUID_ATTR = OID
    -> AttributeManager
AttributeManager
    ATTR_TABLE:
      RENAME_SET_VALUE xtf_id > XTF_ID
      RENAME_SET_VALUE publiziertAb > PUBLIZIERTAB
      RENAME_SET_VALUE MetadatenGeobasisdaten > METAGEO_DE
      SET_TO METAGEO_FR = @Value(METAGEO_DE)
    -> AttributeValueMapper
Note: law_status mappen
AttributeValueMapper
    DIRECTION = Forward (Source To Destination)
    LUT = inKraft,inForce,laufendeAenderung,runningModification
    SRC = Rechtsstatus
    VAL_ATTR = law_status
    -> AttributeValueMapper_2
Note: RES_ID mappen
AttributeValueMapper_2
    DIRECTION = Forward (Source To Destination)
    LUT = inKraft,1,laufendeAenderung,2
    SRC = Rechtsstatus
    VAL_ATTR = RES_ID
    -> AttributeKeeper
AttributeKeeper
    KEEP_ATTRS = Linie_LV95,METAGEO_DE,law_status,ZustaendigeStelle,METAGEO_FR,Punkt_LV95,RES_ID,XTF_ID,Eigentumsbeschraenkung,Flaeche_LV95,PUBLIZIERTAB,OID,fme_type
    -> UUIDGenerator_2_OUTPUT_323 (output)
UUIDGenerator_2_OUTPUT_323 (output)

FME custom transformer DARSTELLUNSDIENST

Parameters:
- LIEFEREINHEIT =   # Liefereinheit
- LEGEND_BASEURL =   # Legenden-Basis-URL

UUIDGenerator_INPUT_349 (input)
    -> UUIDGenerator
Note: UUID generieren
UUIDGenerator
    UUID_ATTR = DAR_OID
    -> AttributeManager
AttributeManager
    ATTR_TABLE:
      RENAME_SET_VALUE xtf_id > DAR_XTF_ID
      RENAME_SET_VALUE VerweisWMS > DAR_VERWEISWMS_DE
      SET_TO DAR_VERWEISWMS_FR = @Value(DAR_VERWEISWMS_DE)
    -> StringConcatenator_2
Note: "Unser" Legendenbild (de) einfügen
StringConcatenator_2
    ACTION = Create New Attribute
    PARM_LINE = $(LEGEND_BASEURL)$(LIEFEREINHEIT)_de.png
    VAL_ATTR = DAR_LEGENDEIMWEB_DE
    -> StringConcatenator_3
Note: "Unser" Legendenbild (fr) einfügen
StringConcatenator_3
    ACTION = Create New Attribute
    PARM_LINE = $(LEGEND_BASEURL)$(LIEFEREINHEIT)_fr.png
    VAL_ATTR = DAR_LEGENDEIMWEB_FR
    -> JSONTemplater_5 [ROOT]
Note: legend_at_web-Attribut als JSON-String / aufbauen.
JSONTemplater_5
    RESULT_ATTRIBUTE = legend_at_web
    ROOT_QUERY_EXPR:
      {
          "fr": fme:get-attribute("DAR_LEGENDEIMWEB_FR"),
          "de": fme:get-attribute("DAR_LEGENDEIMWEB_DE")
      }
    VISIBLE_QUERY_VALIDATE = Yes
    -> StringReplacer_2
Note: Koordinatensystem ersetzen
StringReplacer_2
    CASE = no
    FIND_TEXT = EPSG:21781
    NO_MATCH = _FME_NO_OP_
    REGEXP = no
    REPLACE_TEXT = EPSG:2056
    SRC_ATTRS = DAR_VERWEISWMS_DE,DAR_VERWEISWMS_FR
    -> AttributeKeeper
AttributeKeeper
    KEEP_ATTRS = legend_at_web,DAR_OID,DAR_VERWEISWMS_DE,DAR_LEGENDEIMWEB_DE,DAR_LEGENDEIMWEB_FR,DAR_LIEFEREINHEIT,DAR_VERWEISWMS_FR,DAR_XTF_ID
    KEEP_LIST = Legende{}.ArtCode Legende{}.ArtCodeliste Legende{}.LegendeText{} Legende{}.LegendeText{}.LocalisedText{} Legende{}.LegendeText{}.LocalisedText{}.Language Legende{}.LegendeText{}.LocalisedText{}.Text Legende{}.LegendeText{}.LocalisedText{}.xtf_class Legende{}.LegendeText{}.xtf_class Legende{}.SubThema Legende{}.Symbol Legende{}.Thema Legende{}.WeiteresThema Legende{}.xtf_class
    -> AttributeCopier_OUTPUT_233 (output)
AttributeCopier_OUTPUT_233 (output)

FME custom transformer AMT

Parameters:
- LIEFEREINHEIT =   # Liefereinheit

AttributeCreator_2_INPUT_184 (input)
    -> AttributeCreator_2
Note: Mehrsprachige Felder / deklarieren
AttributeCreator_2
    ATTR_TABLE = SET_TO multilangfields = Name
    -> PythonCaller_2
Note: Mehrsprachiger Text / verarbeiten
PythonCaller_2
    NEW_ATTRIBUTES = Name_DE Name_FR
    PYTHONSYMBOL = processMultilangFields
    -> AttributeManager
AttributeManager
    ATTR_TABLE:
      RENAME_SET_VALUE xtf_id > AMT_XTF_ID
      RENAME_SET_VALUE AmtImWeb > AMT_AMTIMWEB_DE
      RENAME_SET_VALUE Name_DE > AMT_NAME_DE
      RENAME_SET_VALUE Name_FR > AMT_NAME_FR
      SET_TO AMT_AMTIMWEB_FR = @Value(AMT_AMTIMWEB_DE)
    -> UUIDGenerator
UUIDGenerator
    UUID_ATTR = AMT_OID
    -> JSONTemplater_5 [ROOT]
Note: name-Attribut als JSON-String / aufbauen.
JSONTemplater_5
    RESULT_ATTRIBUTE = name
    ROOT_QUERY_EXPR:
      {
          "fr": fme:get-attribute("AMT_NAME_FR"),
          "de": fme:get-attribute("AMT_NAME_DE")
      }
    VISIBLE_QUERY_VALIDATE = Yes
    -> AttributeKeeper
AttributeKeeper
    KEEP_ATTRS = AMT_LIEFEREINHEIT,AMT_XTF_ID,AMT_NAME_DE,AMT_AMTIMWEB_DE,name,AMT_AMTIMWEB_FR,AMT_OID,UID,AMT_NAME_FR
    -> AttributeRemover_3_OUTPUT_236 (output)
AttributeRemover_3_OUTPUT_236 (output)

FME custom transformer LEGEND_ENTRY

Parameters:
- LIEFEREINHEIT =
- ARTCODE = @Value(ArtCode)   # ArtCode
- ARTCODELISTE = @Value(ArtCodeliste)   # ArtCodeliste
- DAR_OID = @Value(DAR_OID)   # Dar Oid
- EIB_ARTCODE = @Value(EIB_ARTCODE)   # Eib Artcode
- EIB_LEGENDESYMBOL_DE = @Value(EIB_LEGENDESYMBOL_DE)   # Eib Legendesymbol De
- SUBTHEMA = @Value(SubThema)   # SubThema
- SYMBOL = @Value(Symbol)   # Symbol
- THEMA = @Value(Thema)   # Thema
- WEITERESTHEMA = @Value(WeiteresThema)   # WeiteresThema
- XTF_CLASS = @Value(xtf_class)   # Xtf Class

Input (input)
    -> AttributeManager
AttributeManager
    ATTR_TABLE:
      RENAME_SET_VALUE ArtCode > type_code
      RENAME_SET_VALUE ArtCodeliste > type_code_list
      RENAME_SET_VALUE DAR_OID > view_service_id
      REMOVE EIB_ARTCODE
      RENAME_SET_VALUE EIB_LEGENDESYMBOL_DE > symbol_url
      REMOVE Symbol
      REMOVE xtf_class
      SET_TO multilangfields = Text
    -> UUIDGenerator
UUIDGenerator
    UUID_ATTR = id
    -> AttributeCreator
Note: Mehrsprachige Felder / deklarieren
AttributeCreator
    ATTR_TABLE = SET_TO multilangfields = Text
    -> PythonCaller
Note: Mehrsprachiger Text / verarbeiten
PythonCaller
    NEW_ATTRIBUTES = Text_DE Text_FR
    PYTHONSYMBOL = processMultilangFields
    -> JSONTemplater_5 [ROOT]
Note: legend_text-Attribut als JSON-String / aufbauen.
JSONTemplater_5
    RESULT_ATTRIBUTE = legend_text
    ROOT_QUERY_EXPR:
      {
          "fr": fme:get-attribute("Text_FR"),
          "de": fme:get-attribute("Text_DE")
      }
    VISIBLE_QUERY_VALIDATE = Yes
    -> AttributeValueMapper
Note: Topic mappen
AttributeValueMapper
    DIRECTION = Forward (Source To Destination)
    LUT = BaulinienEisenbahnanlagen,RailwaysBuildingLines,BaulinienFlughafenanlagen,AirportsBuildingLines,BaulinienKantonsstrassen,ch.BE.CantonalStreetBuildingLines,BaulinienNationalstrassen,MotorwaysBuildingLines,BelasteteStandorte,ContaminatedSites,BelasteteStandorteMilitaer,ContaminatedMilitarySites,BelasteteStandorteOeffentlicherVerkehr,ContaminatedPublicTransportSites,BelasteteStandorteZivileFlugplaetze,ContaminatedCivilAviationSites,Grundwasserschutzareale,GroundwaterProtectionSites,Grundwasserschutzzonen,GroundwaterProtectionZones,KantonaleNutzungsplanung,ch.BE.CantonalLandUsePlans,KantonaleWaldbaulinien,ch.BE.CantonalForestDistanceLines,Laermempfindlichkeitsstufen,NoiseSensitivityLevels,Nutzungsplanung,LandUsePlans,ProjektierungszonenEisenbahnanlagen,RailwaysProjectPlanningZones,ProjektierungszonenFlughafenanlagen,AirportsProjectPlanningZones,ProjektierungszonenNationalstrassen,MotorwaysProjectPlaningZones,RegionaleNutzungsplanung,ch.BE.RegionalLandUsePlans,RegionaleWaldbaulinien,ch.BE.RegionalForestDistanceLines,SicherheitszonenplanFlughafen,AirportsSecurityZonePlans,Waldabstandslinien,ForestDistanceLines,Waldgrenzen,ForestPerimeters,KantonaleNaturschutzgebiete,ch.BE.CantonalNatureReserves,GeschuetzteGeologischeObjekte,ch.BE.RegionalProtectedGeologicalObjects,GeschuetzteBotanischeObjekte,ch.BE.RegionalProtectedBotanicalObjects
    SRC = Thema
    VAL_ATTR = topic
    -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = symbol_binary
    TARGET_ATTR_ENCODING = auto-detect
    TARGET_URL = @Value(symbol_url)
    TRANSFER_TIMEOUT_LENGTH = 90
    USE_COOKIES = No
    VERIFY_SSL_CERTIFICATES = Yes
    -> BinaryEncoder_2
BinaryEncoder_2
    ATTR_TO_ENCODE = symbol_binary
    DEST_ATTR = symbol
    ENCODING_TYPE = Base64
    -> AttributeKeeper
AttributeKeeper
    KEEP_ATTRS = topic,type_code,type_code_list,legend_text,id,symbol,symbol_url,view_service_id,liefereinheit
    -> Output (output)
Output (output)

FME custom transformer HINWEISVORSCHRIFT

Parameters:
- LIEFEREINHEIT =   # Liefereinheit

HINWEISVORSCHRIFT_UUIDGenerator_INPUT_220 (input)
    -> UUIDGenerator_2
UUIDGenerator_2
    UUID_ATTR = HIV_ID
    -> ListConcatenator
Note: ArtikelNummer in ein / Feld konkatenieren
ListConcatenator
    DROP_EMPTY_PARTS = No
    LIST_ATTR = ArtikelNr{}.value
    SEP = ,
    VAL_ATTR = HIV_ARTNR
    -> AttributeRenamer_2
AttributeRenamer_2
    ATTR_TABLE = RENAME_SET_DEFAULT xtf_id > HIV_XTF_ID
    -> AttributeKeeper
AttributeKeeper
    KEEP_ATTRS = Vorschrift,HIV_ARTNR,HIV_ID,HIV_XTF_ID,Eigentumsbeschraenkung
    -> HINWEISVORSCHRIFT_AttributeRenamer_OUTPUT_212 (output)
HINWEISVORSCHRIFT_AttributeRenamer_OUTPUT_212 (output)

FME custom transformer ARTIKEL

Parameters:
- LIEFEREINHEIT =   # Liefereinheit

SQLExecutor_8_INITIATOR_245 (input)
    -> AttributeValueMapper
Note: law_status mappen
AttributeValueMapper
    DIRECTION = Forward (Source To Destination)
    LUT = inKraft,inForce,laufendeAenderung,runningModification
    SRC = Rechtsstatus
    VAL_ATTR = law_status
    -> AttributeValueMapper_2
Note: RES_ID mappen
AttributeValueMapper_2
    DIRECTION = Forward (Source To Destination)
    LUT = inKraft,1,laufendeAenderung,2
    SRC = Rechtsstatus
    VAL_ATTR = RES_ID
    -> AttributeCreator_4
Note: Mehrsprachige Felder / deklarieren
AttributeCreator_4
    ATTR_TABLE = SET_TO multilangfields = Text,TextImWeb
    -> PythonCaller_4
Note: Mehrsprachiger Text / verarbeiten
PythonCaller_4
    NEW_ATTRIBUTES = Text_DE Text_FR TextImWeb_DE TextImWeb_FR
    PYTHONSYMBOL = processMultilangFields
    -> JSONTemplater_2 [ROOT]
Note: title-Attribut als JSON-String / aufbauen.
JSONTemplater_2
    RESULT_ATTRIBUTE = text
    ROOT_QUERY_EXPR:
      {
          "fr": fme:get-attribute("Text_FR"),
          "de": fme:get-attribute("Text_DE")
      }
    VISIBLE_QUERY_VALIDATE = Yes
    -> UUIDGenerator
UUIDGenerator
    UUID_ATTR = ART_OID
    -> DateFormatter_4
Note: publiziertAb / formatieren
DateFormatter_4
    DATE_ATTR = publiziertAb
    FMT = FME Date (%Y%m%d)
    INVALID_DATE_VALUE = _FME_NO_OP_
    SRCFMT = Unknown - Automatic Detection
    -> AttributeRenamer
AttributeRenamer
    ATTR_TABLE:
      RENAME_SET_DEFAULT publiziertAb > ART_PUBLIZIERTAB
      RENAME_SET_DEFAULT TextImWeb_DE > ART_TEXTIMWEB_DE
      RENAME_SET_DEFAULT Nr > ART_NR
      RENAME_SET_DEFAULT Text_DE > ART_TEXT_DE
      RENAME_SET_DEFAULT Text_FR > ART_TEXT_FR
      RENAME_SET_DEFAULT xtf_id > ART_XTF_ID
      RENAME_SET_DEFAULT TextImWeb_FR > ART_TEXTIMWEB_FR
    -> AttributeKeeper
AttributeKeeper
    KEEP_ATTRS = ART_PUBLIZIERTAB,ART_XTF_ID,ART_NR,ART_TEXTIMWEB_DE,ART_LIEFEREINHEIT,RES_ID,ART_TEXTIMWEB_FR,ART_TEXT_DE,Dokument,text,ART_OID,ART_TEXT_FR
    -> PythonCaller_4_OUTPUT_255 (output)
PythonCaller_4_OUTPUT_255 (output)

FME custom transformer HINWEIDOK

Parameters:
- LIEFEREINHEIT =   # Liefereinheit

UUIDGenerator_INPUT_184 (input)
    -> UUIDGenerator
Note: Association hat keine ID, / deshalb wird UUID erzeugt
UUIDGenerator
    UUID_ATTR = HWD_ID
    -> ListConcatenator
Note: ArtikelNr in ein Feld / konkatenieren
ListConcatenator
    DROP_EMPTY_PARTS = No
    LIST_ATTR = ArtikelNr{}.value
    SEP = ,
    VAL_ATTR = HWD_ARTNR
    -> AttributeRenamer
AttributeRenamer
    ATTR_TABLE = RENAME_SET_DEFAULT xtf_id > HWD_XTF_ID
    -> AttributeKeeper
AttributeKeeper
    KEEP_ATTRS = HWD_XTF_ID,Hinweis,HWD_ID,HWD_ARTNR,Ursprung
    -> UUIDGenerator_OUTPUT_184 (output)
UUIDGenerator_OUTPUT_184 (output)
