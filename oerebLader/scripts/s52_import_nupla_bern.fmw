FME workspace s52_import_nupla_bern.fmw

Parameters:
- ITF_FILE =   # Interlis-Datei
- MODELLABLAGE =   # Modellablage
- OEREB2_DATABASE =   # Oereb2-Database
- OEREB2_USERNAME =   # Oereb2-Username
- OEREB2_PASSWORD =   # Oereb2-Passwort
- GEODB_DATABASE =   # GeoDB-Database
- GEODB_USERNAME =   # GeoDB-Username
- GEODB_PASSWORD =   # GeoDB-Passwort
- BFSNR =   # BFS-Nummer
- GEMNAME =   # Gemeindename
- LOGFILE =   # Logfile
- LIEFEREINHEIT =   # Liefereinheit
- EXCEL_AMT =   # Excel-File AMT
- INPUT_RV_DIR =   # Input-Verzeichnis RV
- OUTPUT_RV_DIR =   # Output-Verzeichnis RV
- OUTPUT_RV_URL =   # Output-Url RV
- EXCEL_DARSTELLUNG =   # Excel-File DARSTELLUNG
- NPL_WMS_BASE =   # WMS-Basis-URL
- LEGEND_BASEURL =   # Legenden-Basis-URL
- LEGEND_BASEDIR =   # Legenden-Basisverzeichnis
- LEGEND_INPUTDIR =
- CREATE_LINETABLES =   # Create Linetables
- GEODB_PG_DATABASE =
- GEODB_PG_USERNAME =
- GEODB_PG_PASSWORD =
- GEODB_PG_HOST =
- GEODB_PG_PORT =
- AMT_OID = return "ch.be.bve.agi." + FME_MacroValues['BFSNR']   # Python Script

Readers:
- XLSXR_1: XLSXR from $(EXCEL_AMT)
- ch.ehi.fme.Main_1: ch.ehi.fme.Main from $(ITF_FILE) in EPSG:2056
- XLSXR_2: XLSXR from $(EXCEL_DARSTELLUNG)

Writers:
- ORACLE8I_DB_1: ORACLE8I_DB to $(OEREB2_DATABASE)
- GEODATABASE_SDE_1: GEODATABASE_SDE to sde
- GEODATABASE_SDE_2: GEODATABASE_SDE to sde
- FILECOPY_1: FILECOPY to C:\Windows\Temp
- FILECOPY_2: FILECOPY to C:\Windows\Temp
- POSTGIS_1: POSTGIS to $(GEODB_PG_DATABASE) in EPSG:2056

Note: UE_AaretalschutzgebietUmrandungslinie
DM16NplBE_Bern.Nutzungsplanung.UE_AaretalschutzgebietUmrandungslinie (reader ch.ehi.fme.Main_1)
    attributes: xtf_id xtf_char(200), DarstellungCode xtf_char(5)
    -> AttributeCreator_2
AttributeCreator_2
    ATTR_LIST = ART,Aaretalschutzgebiet
    -> NUPLA_ABGRZ (writer GEODATABASE_SDE_2)
    -> BulkAttributeRenamer_11
Note: GN_BauweiseAbgrenzung
DM16NplBE_Bern.Nutzungsplanung.GN_BauweiseAbgrenzung (reader ch.ehi.fme.Main_1)
    attributes: xtf_id xtf_char(200), DarstellungCode xtf_char(5)
    -> AttributeCreator_10
AttributeCreator_10
    ATTR_LIST = ART,Bauweise
    -> NUPLA_ABGRZ (writer GEODATABASE_SDE_2)
    -> BulkAttributeRenamer_11
BulkAttributeRenamer_11
    ATTRCHOICE = All Attributes
    CASE_CHANGE_TYPE = lower
    MODE_CHOICE = RENAME
    PATTERN_ACTION_DISP = CASECHANGE
    -> nupla_abgrz (writer POSTGIS_1)
Note: geodb.nupla_abgrz
nupla_abgrz (writer POSTGIS_1)
    attributes: bfsnr int2, gemname varchar(50), art varchar(30), darst_c varchar(5)
Note: NUPLA_ABGRZ
NUPLA_ABGRZ (writer GEODATABASE_SDE_2)
    attributes: BFSNR smallint, GEMNAME char(50), ART char(30), DARST_C char(5)
Note: Amt vorbereiten
Amt_vorbereiten: Amt vorbereiten
    AMTIMWEB = @Value(AmtImWeb)
    NAME = @Value(Name)
    UID_AMT = @Value(UID_Amt)
    XTF_ID = @Value(xtf_id)
    AMT -> Dokument_vorbereiten [Amt]
    AMT -> FeatureMerger_3 [REQUESTOR]
    AMT -> UE_Ueberlagerung [Alle_Aemter]
    AMT -> UE_Abstandslinie [Alle_Aemter]
    AMT -> NH_NaturHeimatSchutz [Alle_Aemter]
    AMT -> WE_WegRoute [Alle_Aemter]
    AMT -> GW_Gewaesser [Alle_Aemter]
    AMT -> GR_Gewaesserraum [Alle_Aemter]
    AMT -> GN_Bauweise [AlleÄmter]
    AMT -> FeatureMerger_4 [REQUESTOR]
    AMT -> GN_Nutzungszonen [Alle_Aemter]
    AMT -> GN_ZPPUEO [AlleAemter]
    AMT -> VE_Vor_Einschraenkung [AlleAemter]
Note: NUPLA_UELARMES
NUPLA_UELARMES (writer GEODATABASE_SDE_2)
    attributes: BFSNR smallint, GEMNAME char(50), RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10)
BulkAttributeRenamer_10
    ATTRCHOICE = All Attributes
    CASE_CHANGE_TYPE = lower
    MODE_CHOICE = RENAME
    PATTERN_ACTION_DISP = CASECHANGE
    -> nupla_uelarmes (writer POSTGIS_1)
Note: geodb.nupla_uelarmes
nupla_uelarmes (writer POSTGIS_1)
    attributes: bfsnr int2, gemname varchar(50), rvs_id varchar(100), genehm timestamp, inkraft timestamp, beschrieb varchar(80), qualitaet int2, verbindlkt int2, kantart int2,BTREE, zonenabk varchar(12), bez varchar(150), planbeschr varchar(150), bemerk varchar(80), darst_c varchar(5), datenverw varchar(36), zustaendig varchar(36), bundesart varchar(10)
Note: NUPLA_UEWAABL
NUPLA_UEWAABL (writer GEODATABASE_SDE_2)
    attributes: BFSNR smallint, GEMNAME char(50), GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, RVS_ID char(100)
BulkAttributeRenamer_9
    ATTRCHOICE = All Attributes
    CASE_CHANGE_TYPE = lower
    MODE_CHOICE = RENAME
    PATTERN_ACTION_DISP = CASECHANGE
    -> nupla_uewaabl (writer POSTGIS_1)
Note: geodb.nupla_uewaabl
nupla_uewaabl (writer POSTGIS_1)
    attributes: bfsnr int2, gemname varchar(50), rvs_id varchar(100), genehm timestamp, inkraft timestamp, beschrieb varchar(80), qualitaet int2, verbindlkt int2, kantart int2,BTREE, linienabk varchar(12), bez varchar(150), planbeschr varchar(150), bemerk varchar(80), darst_c varchar(5), datenverw varchar(36), zustaendig varchar(36), bundesart varchar(10), nz float4, nz_art int2, gruenfz float4
Note: OEREB2.PUNKT
PUNKT (writer GEODATABASE_SDE_1)
    attributes: PUN_OID char(128), PUN_XTF_ID char(128), PUN_PUBLIZIERTAB date, PUN_METAGEO_DE char(1023), PUN_METAGEO_FR char(1023), PUN_LIEFEREINHEIT integer, EIB_OID char(128), AMT_OID char(128), RES_ID integer
Note: NUPLA_UEPT
NUPLA_UEPT (writer GEODATABASE_SDE_2)
    attributes: BFSNR smallint, GEMNAME char(50), RVS_ID char(100), GENEHM date, INKRAFT date, BESCHRIEB char(80), QUALITAET smallint, VERBINDLKT smallint, KANTART smallint, PUNKTABK char(12), BEZ char(150), PLANBESCHR char(150), BEMERK char(80), DARST_C char(5), DATENVERW char(36), ZUSTAENDIG char(36), BUNDESART char(10), ORI float, BEDEUT smallint, SCHUTZG smallint
BulkAttributeRenamer_8
    ATTRCHOICE = All Attributes
    CASE_CHANGE_TYPE = lower
    MODE_CHOICE = RENAME
    PATTERN_ACTION_DISP = CASECHANGE
    -> nupla_uept (writer POSTGIS_1)
Note: geodb.nupla_uept
nupla_uept (writer POSTGIS_1)
    attributes: bfsnr int2, gemname varchar(50), rvs_id varchar(100), genehm timestamp, inkraft timestamp, beschrieb varchar(80), qualitaet int2, verbindlkt int2, kantart int2,BTREE, punktabk varchar(12), bez varchar(150), planbeschr varchar(150), bemerk varchar(80), darst_c varchar(5), datenverw varchar(36), zustaendig varchar(36), bundesart varchar(10), ori float4, bedeut int2, schutzg int2
FeatureHolder_4
    -> NUPLA_UELN (writer GEODATABASE_SDE_2)
    -> BulkAttributeRenamer_7
BulkAttributeRenamer_7
    ATTRCHOICE = All Attributes
    CASE_CHANGE_TYPE = lower
    MODE_CHOICE = RENAME
    PATTERN_ACTION_DISP = CASECHANGE
    -> nupla_ueln (writer POSTGIS_1)
Note: geodb.nupla_ueln
nupla_ueln (writer POSTGIS_1)
    attributes: bfsnr int2, gemname varchar(50), rvs_id varchar(100), genehm timestamp, inkraft timestamp, beschrieb varchar(80), qualitaet int2, verbindlkt int2, kantart int2,BTREE, linienabk varchar(12), bez varchar(150), planbeschr varchar(150), bemerk varchar(80), darst_c varchar(5), datenverw varchar(36), zustaendig varchar(36), bundesart varchar(10), nz float4, nz_art int2, gruenfz float4, bedeut int2, schutzg int2, gw_nat int2, gw_bed int2, abstlinks float4, abstrechts float4, abstdef int2, status int2
Note: NUPLA_UELN
NUPLA_UELN (writer GEODATABASE_SDE_2)
    attributes: BFSNR smallint, GEMNAME char(50), RVS_ID char(100), GENEHM date, INKRAFT date, BESCHRIEB char(80), QUALITAET smallint, VERBINDLKT smallint, KANTART smallint, LINIENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, ABSTLINKS float, ABSTRECHTS float, ABSTDEF smallint, STATUS smallint
Note: OEREB2.LINIE
LINIE (writer GEODATABASE_SDE_1)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
Note: Verwendete Aemter weiter- / verarbeiten
FeatureHolder_2
    -> FeatureMerger_4 [SUPPLIER]
    -> FeatureMerger_3 [SUPPLIER]
FeatureMerger_4
    IGNORE_NULLS = Yes
    JOIN_KEYS = @Value(AMT_ID) @Value(ZUSTAENDIG) AUTO
    MERGE_TYPE = Attributes Only
    PROCESS_DUPS = No
    SUPPLIERS_FIRST = No
    SUPPLIER_PREFIX_DUMMY = YES
    MERGED -> AttributeRemover_7
FeatureMerger_3
    IGNORE_NULLS = Yes
    JOIN_KEYS = @Value(AMT_ID) @Value(DATENVERW) AUTO
    MERGE_TYPE = Attributes Only
    PROCESS_DUPS = No
    SUPPLIERS_FIRST = No
    SUPPLIER_PREFIX_DUMMY = YES
    MERGED -> AttributeRemover_7
AttributeRemover_7
    REMOVE_ATTRS = DATENVERW,ZUSTAENDIG
    -> NUPLA_AMTT (writer GEODATABASE_SDE_2)
    -> BulkAttributeRenamer_12
BulkAttributeRenamer_12
    ATTRCHOICE = All Attributes
    CASE_CHANGE_TYPE = lower
    MODE_CHOICE = RENAME
    PATTERN_ACTION_DISP = CASECHANGE
    -> nupla_amtt (writer POSTGIS_1)
Note: geodb.nupla_amtt
nupla_amtt (writer POSTGIS_1)
    attributes: bfsnr int2, gemname varchar(50), amtname varchar(200), uid_amt varchar(15), amtimweb varchar(100), amt_id varchar(36)
Note: NUPLA_AMTT
NUPLA_AMTT (writer GEODATABASE_SDE_2)
    attributes: BFSNR smallint, GEMNAME char(50), AMTNAME char(200), UID_AMT char(15), AMTIMWEB char(100), AMT_ID char(36)
Aggregator
    ACCUM_ATTRS_NAME = Yes
    GROUP_BY = EIB_XTF_ID EIB_OID EIB_PUBLIZIERTAB EIB_AUSSAGE_DE EIB_AUSSAGE_FR EIB_ARTCODE EIB_SORT RES_ID STH_ID DAR_OID EIB_LEGENDESYMBOL_DE EIB_LEGENDESYMBOL_FR filecopy_source_dataset filecopy_dest_dataset
    MODE = Attributes Only
    ORDERED = No
    SEP = ,
    AGGREGATE -> EIGENTUMSBESCHRAENKUNG (writer ORACLE8I_DB_1)
    AGGREGATE -> AttributeRemover
    AGGREGATE -> AttributeKeeper
AttributeKeeper
    KEEP_ATTRS = filecopy_source_dataset,filecopy_dest_dataset
    -> DuplicateRemover_4
DuplicateRemover_4
    KEYATTR = filecopy_source_dataset filecopy_dest_dataset
    UNIQUE -> filecopy (writer FILECOPY_2)
Note: Legendenbilder kopieren
filecopy (writer FILECOPY_2)
Note: OEREB2.EIGENTUMSBESCHRAENKUNG
EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), STH_ID number(10,0), EIB_SORT number(10,0), EIB_LEGENDESYMBOL_DE nvarchar(1023), EIB_LEGENDESYMBOL_FR nvarchar(1023)
AttributeRemover
    REMOVE_ATTRS = _kantart,EIB_LEGENDESYMBOL_DE,filecopy_dest_dataset,EIB_ARTCODE,EIB_PUBLIZIERTAB,STATUS,EIB_SORT,EIB_AUSSAGE_FR,RES_ID,EIB_LEGENDESYMBOL_FR,filecopy_source_dataset,EIB_AUSSAGE_DE,DAR_OID
    -> TestFilter
TestFilter
    DEFAULT_VALUE = UEBRIGE
    TEST_LIST = BOOL_OP,OR,COMPOSITE_TEST,<Unused>,TEST_CLAUSE,"NUM_TEST @Value(STH_ID) = 150",LAERMEMPFINDLICHKEITSSTUFEN,BOOL_OP,OR,COMPOSITE_TEST,<Unused>,TEST_CLAUSE,"NUM_TEST @Value(STH_ID) = 170",WALDBAULINIEN
    LAERMEMPFINDLICHKEITSSTUFEN -> AttributeCreator_9
    WALDBAULINIEN -> AttributeCreator_4
    WALDBAULINIEN -> AttributeCreator_3
    WALDBAULINIEN -> AttributeCreator
    UEBRIGE -> AttributeCreator_5
    UEBRIGE -> AttributeCreator_6
    UEBRIGE -> AttributeCreator_7
    UEBRIGE -> AttributeCreator_8
FeatureHolder_3
    -> NUPLA_UEFL (writer GEODATABASE_SDE_2)
    -> BulkAttributeRenamer_6
BulkAttributeRenamer_6
    ATTRCHOICE = All Attributes
    CASE_CHANGE_TYPE = lower
    MODE_CHOICE = RENAME
    PATTERN_ACTION_DISP = CASECHANGE
    -> nupla_uefl (writer POSTGIS_1)
Note: geodb.nupla_uefl
nupla_uefl (writer POSTGIS_1)
    attributes: bfsnr int2, gemname varchar(50), rvs_id varchar(100), genehm timestamp, inkraft timestamp, beschrieb varchar(80), qualitaet int2, verbindlkt int2, kantart int2, zonenabk varchar(12), bez varchar(150), planbeschr varchar(150), bemerk varchar(80), darst_c varchar(5), datenverw varchar(36), zustaendig varchar(36), bundesart varchar(10), nz float4, nz_art int2, gruenfz float4, bedeut int2, schutzg int2, gw_nat int2, gw_bed int2, ve_gueltig timestamp, ve_beschw int2, ve_thema int2
Note: NUPLA_UEFL
NUPLA_UEFL (writer GEODATABASE_SDE_2)
    attributes: BFSNR smallint, GEMNAME char(50), RVS_ID char(100), GENEHM date, INKRAFT date, BESCHRIEB char(80), QUALITAET smallint, VERBINDLKT smallint, KANTART smallint, ZONENABK char(12), BEZ char(150), PLANBESCHR char(150), BEMERK char(80), DARST_C char(5), DATENVERW char(36), ZUSTAENDIG char(36), BUNDESART char(10), NZ float, NZ_ART smallint, GRUENFZ float, BEDEUT smallint, SCHUTZG smallint, GW_NAT smallint, GW_BED smallint, VE_GUELTIG date, VE_BESCHW smallint, VE_THEMA smallint
Note: OEREB2.FLAECHE
FLAECHE (writer GEODATABASE_SDE_1)
    attributes: FLA_OID char(128), FLA_XTF_ID char(128), FLA_PUBLIZIERTAB date, FLA_METAGEO_DE char(1023), FLA_METAGEO_FR char(1023), FLA_LIEFEREINHEIT integer, EIB_OID char(128), AMT_OID char(128), RES_ID integer
Note: RV weiterverarbeiten
FeatureHolder
    -> FeatureMerger_2 [REQUESTOR]
Note: Dokument vorbereiten
Dokument_vorbereiten: Dokument vorbereiten
    ABKUERZUNG = @Value(Abkuerzung)
    AMT_ID = @Value(AMT_ID)
    AMT_XTF_ID = @Value(AMT_XTF_ID)
    ART_DOKU = @Value(Art_Doku)
    DOKUMENT = @Value(Dokument)
    GEMEINDE = @Value(Gemeinde)
    OFFIZIELLENR = @Value(OffizielleNr)
    OFFIZIELLERTITEL = @Value(OffiziellerTitel)
    TITEL = @Value(Titel)
    XTF_ID = @Value(xtf_id)
    ZUSTAENDIGESTELLE = @Value(ZustaendigeStelle)
    Alle_Dokumente -> HINWEIDOK-IDs_ersetzen [AlleDokumente]
    Alle_Dokumente -> FeatureMerger_2 [SUPPLIER]
    Alle_Dokumente -> FeatureMerger_12 [REQUESTOR]
Note: Alle Dokumente, die in den RV- / Tabellen direkt verlinkt sind.
FeatureMerger_2
    IGNORE_NULLS = Yes
    JOIN_KEYS = @Value(Vorschrift) @Value(VOR_XTF_ID) AUTO
    MERGE_TYPE = Attributes Only
    PROCESS_DUPS = No
    SUPPLIERS_FIRST = No
    SUPPLIER_PREFIX_DUMMY = YES
    MERGED -> AttributeRemover_8
AttributeRemover_8
    REMOVE_ATTRS = Vorschrift,EIB_XTF_ID,VOR_XTF_ID,Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset,AMT_XTF_ID,AMTNAME,UID_AMT,AMTIMWEB,ZUSTAENDIG
    -> UUIDGenerator_7
    -> FeatureMerger_11 [REQUESTOR]
Note: HiinweisWeitereDokumente: / alle IDs ersetzen durch UUIDs / (VOR_OID)
HINWEIDOK-IDs_ersetzen: HINWEIDOK-IDs ersetzen
    ARTIKELNR = @Value(ArtikelNr)
    HINWEIS = @Value(Hinweis)
    ORDNUNGSNUMMER = @Value(Ordnungsnummer)
    URSPRUNG = @Value(Ursprung)
    VOR_OID = @Value(VOR_OID)
    VOR_XTF_ID = @Value(VOR_XTF_ID)
    HINWEIDOK_ID_ersetzt -> HINWEIDOK_flachdruecken [HINWEIDOK]
Note: HINWEIDOK flachdruecken / (mit Views aus Verschnitt- / funktion)
HINWEIDOK_flachdruecken: HINWEIDOK flachdruecken
    HINWEIDOK_flach -> FeatureMerger_11 [SUPPLIER]
FeatureMerger_11
    GEOM_TYPE = Build Polygons
    IGNORE_NULLS = Yes
    JOIN_KEYS = @Value(VOR_OID) @Value(VOR_OIDURSPRUNG) AUTO
    LIST_NAME = duplicates
    MERGE_TYPE = Attributes Only
    PROCESS_DUPS = Yes
    SUPPLIERS_FIRST = No
    SUPPLIER_PREFIX_DUMMY = YES
    MERGED -> AttributeRemover_15
AttributeRemover_15
    REMOVE_ATTRS = HIV_ARTNR,VOR_OID,VOR_OIDURSPRUNG,VOR_OIDHINWEIS
    -> ListExploder
ListExploder
    INDEX_ATTR = _element_index
    LIST_ATTR = duplicates{}
    MODE = List Elements and Original Attributes
    LIST_FOUND -> AttributeRemover_16
AttributeRemover_16
    REMOVE_ATTRS = VOR_OIDURSPRUNG,_element_index
    -> AttributeRenamer_12
AttributeRenamer_12
    ATTR_LIST = VOR_OIDHINWEIS,VOR_OID,""
    -> Aggregator_3
Note: Es kann Duplikate geben / (v.a. in Thun)
Aggregator_3
    ACCUM_ATTRS_NAME = Yes
    GROUP_BY = EIB_OID VOR_OID
    MODE = Attributes Only
    ORDERED = No
    SEP = ,
    AGGREGATE -> UUIDGenerator_7
UUIDGenerator_7
    UUID_ATTR = HIV_ID
    -> AttributeRemover_18
    -> AttributeRemover_19
    -> DuplicateRemover_3
Note: Alle Duplikate entfernen
DuplicateRemover_3
    KEYATTR = EIB_OID VOR_OID
    UNIQUE -> HINVOR (writer ORACLE8I_DB_1)
Note: OEREB2.HINVOR
HINVOR (writer ORACLE8I_DB_1)
    attributes: HIV_ID nvarchar(128), HIV_XTF_ID nvarchar(128), HIV_ARTNR nvarchar(255), HIV_LIEFEREINHEIT number(6,0), EIB_OID nvarchar(128), VOR_OID nvarchar(128)
AttributeRemover_19
    REMOVE_ATTRS = HIV_ID
    -> FeatureMerger_13 [REQUESTOR]
AttributeRemover_18
    REMOVE_ATTRS = HIV_ID,EIB_OID,HIV_ARTNR,VOR_SORT
    -> Aggregator_2
Aggregator_2
    ACCUM_ATTRS_NAME = Yes
    GROUP_BY = VOR_OID
    MODE = Attributes Only
    ORDERED = No
    SEP = ,
    AGGREGATE -> FeatureMerger_12 [SUPPLIER]
FeatureMerger_12
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> FeatureMerger_13 [SUPPLIER]
Note: Merged = REVO und HINW / NotMerged = GEGR
FeatureMerger_13
    IGNORE_NULLS = Yes
    JOIN_KEYS = @Value(VOR_OID) @Value(VOR_OID) AUTO
    MERGE_TYPE = Attributes Only
    PROCESS_DUPS = No
    SUPPLIERS_FIRST = No
    SUPPLIER_PREFIX_DUMMY = YES
    MERGED -> AttributeRenamer_13
    MERGED -> AttributeRemover_2
    NOT_MERGED -> Joiner
AttributeRemover_2
    REMOVE_ATTRS = EIB_OID,HIV_ARTNR,Art_Doku,Gemeinde,Dokument,ZustaendigeStelle,AMT_XTF_ID,AMTNAME,UID_AMT,AMTIMWEB,ZUSTAENDIG
    -> DuplicateRemover
Note: Alle Duplikate entfernen
DuplicateRemover
    KEYATTR = VOR_OFFIZIELLENR VOR_OFFIZIELLERTITEL_FR filecopy_dest_dataset VOR_OID VOR_ABKUERZUNG_FR VOR_ABKUERZUNG_DE VOR_TEXTIMWEB_DE VOR_TITEL_FR VOA_ID VOR_TEXTIMWEB_FR VOR_TITEL_DE VOR_XTF_ID filecopy_source_dataset VOR_OFFIZIELLERTITEL_DE VOR_PUBLIZIERTAB
    UNIQUE -> VORSCHRIFT (writer ORACLE8I_DB_1)
    UNIQUE -> filecopy (writer FILECOPY_1)
filecopy (writer FILECOPY_1)
Note: OEREB2.VORSCHRIFT
VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)
Note: GEGR aus der DB holen. Die / werden separat importiert.
Joiner
    ADDED_FIELDS = VOR_TEXTIMWEB_DE VOR_TITEL_DE VOR_OFFIZIELLERTITEL_DE VOR_ABKUERZUNG_DE VOR_OFFIZIELLENR VOA_ID
    CACHE_SIZE = 5000
    DATASET = $(OEREB2_DATABASE)
    FORMAT = ORACLE8I_DB
    JOIN_KEYS = VOR_OID VOR_OID
    MATCH_RULE_DISPLAY = Must Match Exactly One (1:1)
    ORACLE8I_DB_PASSWORD = $(OEREB2_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(OEREB2_USERNAME)
    PREFETCH_EXHAUSTIVE = Yes
    TABLE = OEREB2.VORSCHRIFT
    JOINED -> AttributeRenamer_13
AttributeRenamer_13
    ATTR_LIST = EIB_OID,RVS_ID,"",VOR_TITEL_DE,TITEL,"",VOR_OFFIZIELLERTITEL_DE,OFFIZTITEL,"",VOR_ABKUERZUNG_DE,ABKUERZUNG,"",VOR_OFFIZIELLENR,OFFIZNR,"",VOR_TEXTIMWEB_DE,DOKUMENT,"",HIV_ARTNR,ARTIKELNR,""
    -> AttributeValueMapper_7
Note: ART aus VOA_ID mappen
AttributeValueMapper_7
    DIRECTION = Forward (Source To Destination)
    LUT = 1,Rechtsvorschrift,2,Gesetzliche Grundlage,3,Hinweis
    SRC = VOA_ID
    VAL_ATTR = ART
    -> Sorter
Sorter
    SORT_PARM = RVS_ID ALPHA ASCENDING ART ALPHA DESCENDING
    SORTED -> AttributeRemover_3
AttributeRemover_3
    REMOVE_ATTRS = VOR_OID,VOR_XTF_ID,Art_Doku,Gemeinde,Dokument,ZustaendigeStelle,VOR_PUBLIZIERTAB,VOA_ID,VOR_TITEL_FR,VOR_OFFIZIELLERTITEL_FR,VOR_ABKUERZUNG_FR,VOR_TEXTIMWEB_FR,filecopy_source_dataset,filecopy_dest_dataset,AMT_XTF_ID,AMTNAME,UID_AMT,AMTIMWEB,_matched_records
    -> DuplicateRemover_2
Note: Alle Duplikate entfernen
DuplicateRemover_2
    KEYATTR = RVS_ID OFFIZNR DOKUMENT OFFIZTITEL ART ARTIKELNR TITEL ABKUERZUNG ZUSTAENDIG
    UNIQUE -> NUPLA_RVST (writer GEODATABASE_SDE_2)
    UNIQUE -> BulkAttributeRenamer_5
BulkAttributeRenamer_5
    ATTRCHOICE = All Attributes
    CASE_CHANGE_TYPE = lower
    MODE_CHOICE = RENAME
    PATTERN_ACTION_DISP = CASECHANGE
    -> nupla_rvst (writer POSTGIS_1)
Note: geodb.nupla_rvst
nupla_rvst (writer POSTGIS_1)
    attributes: bfsnr int2, gemname varchar(50), rvs_id varchar(100), art varchar(40), titel varchar(200), offiztitel varchar(200), abkuerzung varchar(20), offiznr varchar(20), dokument varchar(1023), artikelnr varchar(40), ordnnr int2, zustaendig varchar(36)
Note: NUPLA_RVST
NUPLA_RVST (writer GEODATABASE_SDE_2)
    attributes: BFSNR smallint, GEMNAME char(50), RVS_ID char(100), ART char(40), TITEL char(200), OFFIZTITEL char(200), ABKUERZUNG char(20), OFFIZNR char(20), DOKUMENT char(100), ARTIKELNR char(40), ORDNNR smallint, ZUSTAENDIG char(100)

Bookmark: GN_Grundzone
Note: GN_Bauweise
DM16NplBE_Bern.Nutzungsplanung.GN_Bauweise (reader ch.ehi.fme.Main_1)
    attributes: xtf_id xtf_char(200), Qualitaet xtf_char(255), Datenverwaltungsstelle xtf_char(200), ZustaendigeStelle xtf_char(200), Gebaeudelaenge xtf_int32, Gebaeudelaenge_unbeschraenkt xtf_char(255), Gebaeudetiefe xtf_int32, Gebaeudetiefe_unbeschraenkt xtf_char(255), Typologie xtf_char(255), Genehmigung xtf_date, Inkraftsetzung xtf_date, DarstellungCode xtf_char(5)
    -> GN_Bauweise [GN_Bauweise]
Note: GN_BauweiseRV
DM16NplBE_Bern.Nutzungsplanung.GN_BauweiseRV (reader ch.ehi.fme.Main_1)
    attributes: xtf_id xtf_char(200), Typ xtf_char(200), Vorschrift xtf_char(200), ArtikelNr xtf_char(40)
    -> GN_Bauweise [GN_BauweiseRV]
Note: GN_Grundzone_ZPP_UeO
DM16NplBE_Bern.Nutzungsplanung.GN_Grundzone_ZPP_UeO (reader ch.ehi.fme.Main_1)
    attributes: xtf_id xtf_char(200), ZonentypRef xtf_char(200), Genehmigung xtf_date, Inkraftsetzung xtf_date, Laermempfindlichkeit xtf_char(255), Beschrieb xtf_char(80), Planbeschriftung xtf_char(150), Qualitaet xtf_char(255), Bemerkung xtf_char(80), Flaechenmass xtf_int32
    -> BulkAttributeRenamer_4
BulkAttributeRenamer_4
    ATTRCHOICE = All Attributes
    PATTERN_ACTION_DISP = Add String Prefix
    REPLACE_STR = zpp_
    -> GN_ZPPUEO [GN_GrundzoneZPP_UeO]
Note: GN_Grundzone
DM16NplBE_Bern.Nutzungsplanung.GN_Grundzone (reader ch.ehi.fme.Main_1)
    attributes: xtf_id xtf_char(200), ZonentypRef xtf_char(200), Genehmigung xtf_date, Inkraftsetzung xtf_date, Laermempfindlichkeit xtf_char(255), Beschrieb xtf_char(80), Planbeschriftung xtf_char(150), Qualitaet xtf_char(255), Bemerkung xtf_char(80), Flaechenmass xtf_int32
    -> BulkAttributeRenamer
BulkAttributeRenamer
    ATTRCHOICE = All Attributes
    PATTERN_ACTION_DISP = Add String Prefix
    REPLACE_STR = gz_
    -> GN_Nutzungszonen [GN_Grundzone]
    -> GN_Bauklassen [GN_Grundzone]
Note: GN_Zonentyp
DM16NplBE_Bern.Nutzungsplanung.GN_Zonentyp (reader ch.ehi.fme.Main_1)
    attributes: xtf_id xtf_char(200), Verbindlichkeit xtf_char(255), KantArt xtf_char(255), Abkuerzung xtf_char(12), Bezeichnung xtf_char(150), BR_Nutzungsart xtf_char(80), BR_Nutzungsmass xtf_char(80), Nutzungsziffer xtf_decimal(4,2), Nutzungsziffer_Art xtf_char(255), Gruenflaechenziffer xtf_decimal(4,2), Bemerkung xtf_char(80), Datenverwaltungsstelle xtf_char(200), ZustaendigeStelle xtf_char(200), Nutzungszone xtf_char(255), DarstellungCodeNZ xtf_char(5), Bauklasse xtf_char(255), DarstellungCodeBK xtf_char(5)
    -> BulkAttributeRenamer_2
BulkAttributeRenamer_2
    ATTRCHOICE = All Attributes
    PATTERN_ACTION_DISP = Add String Prefix
    REPLACE_STR = zt_
    -> GN_Nutzungszonen [GN_Zonentyp]
    -> GN_Bauklassen [GN_Zonentyp]
    -> GN_ZPPUEO [GN_Zonentyp]
Note: GN_ZonentypRV
DM16NplBE_Bern.Nutzungsplanung.GN_ZonentypRV (reader ch.ehi.fme.Main_1)
    attributes: xtf_id xtf_char(200), Typ xtf_char(200), Vorschrift xtf_char(200), ArtikelNr xtf_char(40)
    -> BulkAttributeRenamer_3
BulkAttributeRenamer_3
    ATTRCHOICE = All Attributes
    PATTERN_ACTION_DISP = Add String Prefix
    REPLACE_STR = rv_
    -> GN_Nutzungszonen [GN_ZonentypRV]
    -> GN_Bauklassen [GN_ZonentypRV]
    -> GN_ZPPUEO [GN_ZonentypRV]
GN_Bauklassen
    BFSNR = $(BFSNR)
    GEODB_DATABASE = $(GEODB_DATABASE)
    GEODB_PASSWORD = $(GEODB_PASSWORD)
    GEODB_USERNAME = $(GEODB_USERNAME)
    GZ_BEMERKUNG = @Value(gz_Bemerkung)
    GZ_BESCHRIEB = @Value(gz_Beschrieb)
    GZ_FLAECHENMASS = @Value(gz_Flaechenmass)
    GZ_GENEHMIGUNG = @Value(gz_Genehmigung)
    GZ_INKRAFTSETZUNG = @Value(gz_Inkraftsetzung)
    GZ_LAERMEMPFINDLICHKEIT = @Value(gz_Laermempfindlichkeit)
    GZ_PLANBESCHRIFTUNG = @Value(gz_Planbeschriftung)
    GZ_QUALITAET = @Value(gz_Qualitaet)
    GZ_XTF_ID = @Value(gz_xtf_id)
    GZ_ZONENTYPREF = @Value(gz_ZonentypRef)
    LEGEND_BASEDIR = $(LEGEND_BASEDIR)
    LEGEND_BASEURL = $(LEGEND_BASEURL)
    LEGEND_INPUTDIR = $(LEGEND_INPUTDIR)
    RV_ARTIKELNR = @Value(rv_ArtikelNr)
    RV_TYP = @Value(rv_Typ)
    RV_VORSCHRIFT = @Value(rv_Vorschrift)
    RV_XTF_ID = @Value(rv_xtf_id)
    ZT_ABKUERZUNG = @Value(zt_Abkuerzung)
    ZT_BAUKLASSE = @Value(zt_Bauklasse)
    ZT_BEMERKUNG = @Value(zt_Bemerkung)
    ZT_BEZEICHNUNG = @Value(zt_Bezeichnung)
    ZT_BR_NUTZUNGSART = @Value(zt_BR_Nutzungsart)
    ZT_BR_NUTZUNGSMASS = @Value(zt_BR_Nutzungsmass)
    ZT_DARSTELLUNGCODEBK = @Value(zt_DarstellungCodeBK)
    ZT_DARSTELLUNGCODENZ = @Value(zt_DarstellungCodeNZ)
    ZT_DATENVERWALTUNGSSTELLE = @Value(zt_Datenverwaltungsstelle)
    ZT_GRUENFLAECHENZIFFER = @Value(zt_Gruenflaechenziffer)
    ZT_KANTART = @Value(zt_KantArt)
    ZT_NUTZUNGSZIFFER = @Value(zt_Nutzungsziffer)
    ZT_NUTZUNGSZIFFER_ART = @Value(zt_Nutzungsziffer_Art)
    ZT_NUTZUNGSZONE = @Value(zt_Nutzungszone)
    ZT_VERBINDLICHKEIT = @Value(zt_Verbindlichkeit)
    ZT_XTF_ID = @Value(zt_xtf_id)
    ZT_ZUSTAENDIGESTELLE = @Value(zt_ZustaendigeStelle)
    EIGENTUMSBESCHRAENKUNG -> Aggregator
    FLAECHE -> FLAECHE (writer GEODATABASE_SDE_1)
    HINVOR -> FeatureHolder
GN_Bauweise
    AMTIMWEB = @Value(AMTIMWEB)
    AMTNAME = @Value(AMTNAME)
    AMT_ID = @Value(AMT_ID)
    AMT_XTF_ID = @Value(AMT_XTF_ID)
    ARTIKELNR = @Value(ArtikelNr)
    BFSNR = $(BFSNR)
    DARSTELLUNGCODE = @Value(DarstellungCode)
    DATENVERWALTUNGSSTELLE = @Value(Datenverwaltungsstelle)
    GEBAEUDELAENGE = @Value(Gebaeudelaenge)
    GEBAEUDELAENGE_UNBESCHRAENKT = @Value(Gebaeudelaenge_unbeschraenkt)
    GEBAEUDETIEFE = @Value(Gebaeudetiefe)
    GEBAEUDETIEFE_UNBESCHRAENKT = @Value(Gebaeudetiefe_unbeschraenkt)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    LEGEND_BASEDIR = $(LEGEND_BASEDIR)
    LEGEND_BASEURL = $(LEGEND_BASEURL)
    LEGEND_INPUTDIR = $(LEGEND_INPUTDIR)
    QUALITAET = @Value(Qualitaet)
    TYP = @Value(Typ)
    TYPOLOGIE = @Value(Typologie)
    UID_AMT = @Value(UID_AMT)
    VORSCHRIFT = @Value(Vorschrift)
    XTF_ID = @Value(xtf_id)
    ZUSTAENDIGESTELLE = @Value(ZustaendigeStelle)
    EIGENTUMSBESCHRAENKUNG -> Aggregator
    GN_BAUWS -> NUPLA_GNBAUWS (writer GEODATABASE_SDE_2)
    GN_BAUWS -> BulkAttributeRenamer_13
    FLAECHE -> FLAECHE (writer GEODATABASE_SDE_1)
    VerwendeteÄmter -> FeatureHolder_2
    HINVOR -> FeatureHolder
Note: NUPLA_GNBAUWS
NUPLA_GNBAUWS (writer GEODATABASE_SDE_2)
    attributes: BFSNR smallint, GEMNAME char(50), RVS_ID char(100), GENEHM date, INKRAFT date, BWTYP smallint, QUALITAET smallint, GEBL float, GEBLU smallint, GEBT float, GEBTU smallint, GEBLSYM char(2), GEBTSYM char(2), DARST_C char(5), DATENVERW char(15), ZUSTAENDIG char(15)
BulkAttributeRenamer_13
    ATTRCHOICE = All Attributes
    CASE_CHANGE_TYPE = lower
    MODE_CHOICE = RENAME
    PATTERN_ACTION_DISP = CASECHANGE
    -> nupla_gnbauws (writer POSTGIS_1)
Note: geodb.nupla_gnbauws
nupla_gnbauws (writer POSTGIS_1)
    attributes: bfsnr int2, gemname varchar(50), rvs_id varchar(100), genehm timestamp, inkraft timestamp, bwtyp int2, qualitaet int2, gebl float4, geblu int2, gebt float4, gebtu int2, geblsym varchar(2), gebtsym varchar(2), darst_c varchar(5), datenverw varchar(36), zustaendig varchar(36)
GN_ZPPUEO
    AMTIMWEB = @Value(AMTIMWEB)
    AMTNAME = @Value(AMTNAME)
    AMT_ID = @Value(AMT_ID)
    AMT_XTF_ID = @Value(AMT_XTF_ID)
    BFSNR = $(BFSNR)
    GEODB_DATABASE = $(GEODB_DATABASE)
    GEODB_PASSWORD = $(GEODB_PASSWORD)
    GEODB_USERNAME = $(GEODB_USERNAME)
    RV_ARTIKELNR = @Value(rv_ArtikelNr)
    RV_TYP = @Value(rv_Typ)
    RV_VORSCHRIFT = @Value(rv_Vorschrift)
    RV_XTF_ID = @Value(rv_xtf_id)
    UID_AMT = @Value(UID_AMT)
    ZPP_BEMERKUNG = @Value(zpp_Bemerkung)
    ZPP_BESCHRIEB = @Value(zpp_Beschrieb)
    ZPP_FLAECHENMASS = @Value(zpp_Flaechenmass)
    ZPP_GENEHMIGUNG = @Value(zpp_Genehmigung)
    ZPP_INKRAFTSETZUNG = @Value(zpp_Inkraftsetzung)
    ZPP_LAERMEMPFINDLICHKEIT = @Value(zpp_Laermempfindlichkeit)
    ZPP_PLANBESCHRIFTUNG = @Value(zpp_Planbeschriftung)
    ZPP_QUALITAET = @Value(zpp_Qualitaet)
    ZPP_XTF_ID = @Value(zpp_xtf_id)
    ZPP_ZONENTYPREF = @Value(zpp_ZonentypRef)
    ZT_ABKUERZUNG = @Value(zt_Abkuerzung)
    ZT_BAUKLASSE = @Value(zt_Bauklasse)
    ZT_BEMERKUNG = @Value(zt_Bemerkung)
    ZT_BEZEICHNUNG = @Value(zt_Bezeichnung)
    ZT_BR_NUTZUNGSART = @Value(zt_BR_Nutzungsart)
    ZT_BR_NUTZUNGSMASS = @Value(zt_BR_Nutzungsmass)
    ZT_DARSTELLUNGCODEBK = @Value(zt_DarstellungCodeBK)
    ZT_DARSTELLUNGCODENZ = @Value(zt_DarstellungCodeNZ)
    ZT_DATENVERWALTUNGSSTELLE = @Value(zt_Datenverwaltungsstelle)
    ZT_GRUENFLAECHENZIFFER = @Value(zt_Gruenflaechenziffer)
    ZT_KANTART = @Value(zt_KantArt)
    ZT_NUTZUNGSZIFFER = @Value(zt_Nutzungsziffer)
    ZT_NUTZUNGSZIFFER_ART = @Value(zt_Nutzungsziffer_Art)
    ZT_NUTZUNGSZONE = @Value(zt_Nutzungszone)
    ZT_VERBINDLICHKEIT = @Value(zt_Verbindlichkeit)
    ZT_XTF_ID = @Value(zt_xtf_id)
    ZT_ZUSTAENDIGESTELLE = @Value(zt_ZustaendigeStelle)
    GNZPPUEO -> NUPLA_GNZPPUEO (writer GEODATABASE_SDE_2)
    GNZPPUEO -> BulkAttributeRenamer_15
    EIGENTUMSBESCHRAENKUNG -> Aggregator
    FLAECHE -> FLAECHE (writer GEODATABASE_SDE_1)
    HINVOR -> FeatureHolder
    VerwendeteAemter -> FeatureHolder_2
GN_Nutzungszonen
    AMTIMWEB = @Value(AMTIMWEB)
    AMTNAME = @Value(AMTNAME)
    AMT_ID = @Value(AMT_ID)
    AMT_XTF_ID = @Value(AMT_XTF_ID)
    BFSNR = $(BFSNR)
    GEODB_DATABASE = $(GEODB_DATABASE)
    GEODB_PASSWORD = $(GEODB_PASSWORD)
    GEODB_USERNAME = $(GEODB_USERNAME)
    GZ_BEMERKUNG = @Value(gz_Bemerkung)
    GZ_BESCHRIEB = @Value(gz_Beschrieb)
    GZ_FLAECHENMASS = @Value(gz_Flaechenmass)
    GZ_GENEHMIGUNG = @Value(gz_Genehmigung)
    GZ_INKRAFTSETZUNG = @Value(gz_Inkraftsetzung)
    GZ_LAERMEMPFINDLICHKEIT = @Value(gz_Laermempfindlichkeit)
    GZ_PLANBESCHRIFTUNG = @Value(gz_Planbeschriftung)
    GZ_QUALITAET = @Value(gz_Qualitaet)
    GZ_XTF_ID = @Value(gz_xtf_id)
    GZ_ZONENTYPREF = @Value(gz_ZonentypRef)
    RV_ARTIKELNR = @Value(rv_ArtikelNr)
    RV_TYP = @Value(rv_Typ)
    RV_VORSCHRIFT = @Value(rv_Vorschrift)
    RV_XTF_ID = @Value(rv_xtf_id)
    UID_AMT = @Value(UID_AMT)
    ZT_ABKUERZUNG = @Value(zt_Abkuerzung)
    ZT_BAUKLASSE = @Value(zt_Bauklasse)
    ZT_BEMERKUNG = @Value(zt_Bemerkung)
    ZT_BEZEICHNUNG = @Value(zt_Bezeichnung)
    ZT_BR_NUTZUNGSART = @Value(zt_BR_Nutzungsart)
    ZT_BR_NUTZUNGSMASS = @Value(zt_BR_Nutzungsmass)
    ZT_DARSTELLUNGCODEBK = @Value(zt_DarstellungCodeBK)
    ZT_DARSTELLUNGCODENZ = @Value(zt_DarstellungCodeNZ)
    ZT_DATENVERWALTUNGSSTELLE = @Value(zt_Datenverwaltungsstelle)
    ZT_GRUENFLAECHENZIFFER = @Value(zt_Gruenflaechenziffer)
    ZT_KANTART = @Value(zt_KantArt)
    ZT_NUTZUNGSZIFFER = @Value(zt_Nutzungsziffer)
    ZT_NUTZUNGSZIFFER_ART = @Value(zt_Nutzungsziffer_Art)
    ZT_NUTZUNGSZONE = @Value(zt_Nutzungszone)
    ZT_VERBINDLICHKEIT = @Value(zt_Verbindlichkeit)
    ZT_XTF_ID = @Value(zt_xtf_id)
    ZT_ZUSTAENDIGESTELLE = @Value(zt_ZustaendigeStelle)
    GNNUTZBK -> NUPLA_GNNUTZBK (writer GEODATABASE_SDE_2)
    GNNUTZBK -> BulkAttributeRenamer_14
    EIGENTUMSBESCHRAENKUNG -> Aggregator
    FLAECHE -> FLAECHE (writer GEODATABASE_SDE_1)
    HINVOR -> FeatureHolder
    VerwendeteAemter -> FeatureHolder_2
BulkAttributeRenamer_14
    ATTRCHOICE = All Attributes
    CASE_CHANGE_TYPE = lower
    MODE_CHOICE = RENAME
    PATTERN_ACTION_DISP = CASECHANGE
    -> nupla_gnnutzbk (writer POSTGIS_1)
Note: geodb.nupla_gnnutzbk
nupla_gnnutzbk (writer POSTGIS_1)
    attributes: bfsnr int2, gemname varchar(50), rvs_id varchar(100), genehm timestamp, inkraft timestamp, beschrieb varchar(80), qualitaet int2, verbindlkt int2, kantart varchar(10), zonenabk varchar(12), bez varchar(150), planbeschr varchar(150), bemerk varchar(80), darst_c_nz varchar(5), datenverw varchar(36), zustaendig varchar(36), bundesart varchar(10), nz float4, nz_art int2, gruenfz float4, laermes int2, flmass int4, br_nutzart varchar(80), br_nmass varchar(80), nz_typ varchar(100), bk_typ varchar(100), darst_c_bk varchar(5)
Note: NUPLA_GNNUTZBK
NUPLA_GNNUTZBK (writer GEODATABASE_SDE_2)
    attributes: BFSNR smallint, GEMNAME char(50), RVS_ID char(100), GENEHM date, INKRAFT date, BESCHRIEB char(80), QUALITAET smallint, VERBINDLKT smallint, KANTART char(10), ZONENABK char(12), BEZ char(150), PLANBESCHR char(150), BEMERK char(80), DARST_C_NZ char(5), DATENVERW char(15), ZUSTAENDIG char(15), BUNDESART char(10), NZ float, NZ_ART smallint, GRUENFZ float, LAERMES smallint, FLMASS integer, BR_NUTZART char(80), BR_NMASS char(80), NZ_TYP char(100), BK_TYP char(100), DARST_C_BK char(5)
Note: NUPLA_GNZPPUEO
NUPLA_GNZPPUEO (writer GEODATABASE_SDE_2)
    attributes: BFSNR smallint, GEMNAME char(50), RVS_ID char(100), GENEHM date, INKRAFT date, BESCHRIEB char(80), QUALITAET smallint, VERBINDLKT smallint, KANTART char(10), ZONENABK char(12), BEZ char(150), PLANBESCHR char(150), BEMERK char(80), DARST_C char(5), DATENVERW char(36), ZUSTAENDIG char(36), BUNDESART char(10), NZ float, NZ_ART smallint, GRUENFZ float, LAERMES smallint, FLMASS integer, BR_NUTZART char(80), BR_NMASS char(80)
BulkAttributeRenamer_15
    ATTRCHOICE = All Attributes
    CASE_CHANGE_TYPE = lower
    MODE_CHOICE = RENAME
    PATTERN_ACTION_DISP = CASECHANGE
    -> nupla_gnzppueo (writer POSTGIS_1)
Note: geodb.nupla_gnzppueo
nupla_gnzppueo (writer POSTGIS_1)
    attributes: bfsnr int2, gemname varchar(50), rvs_id varchar(100), genehm timestamp, inkraft timestamp, beschrieb varchar(80), qualitaet int2, verbindlkt int2, kantart varchar(10), zonenabk varchar(12), bez varchar(150), planbeschr varchar(150), bemerk varchar(80), darst_c varchar(5), datenverw varchar(36), zustaendig varchar(36), bundesart varchar(10), nz float4, nz_art int2, gruenfz float4, laermes int2, flmass int4, br_nutzart varchar(80), br_nmass varchar(80)

Bookmark: UE_Ueberlagerung
Note: UE_FlaechenelementUeberl
DM16NplBE_Bern.Nutzungsplanung.UE_FlaechenelementUeberl (reader ch.ehi.fme.Main_1)
    attributes: xtf_id xtf_char(200), Genehmigung xtf_date, Inkraftsetzung xtf_date, Objekt xtf_char(200), Beschrieb xtf_char(80), Qualitaet xtf_char(255)
    -> UE_Ueberlagerung [UE_FlaechenelementUeberl]
Note: UE_UeberlagerungZone
DM16NplBE_Bern.Nutzungsplanung.UE_UeberlagerungZone (reader ch.ehi.fme.Main_1)
    attributes: xtf_id xtf_char(200), Verbindlichkeit xtf_char(255), KantArt xtf_char(255), Abkuerzung xtf_char(12), Bezeichnung xtf_char(150), Planbeschriftung xtf_char(150), Nutzungsziffer xtf_decimal(4,2), Nutzungsziffer_Art xtf_char(255), Gruenflaechenziffer xtf_decimal(4,2), Bemerkung xtf_char(80), DarstellungCode xtf_char(5), Datenverwaltungsstelle xtf_char(200), ZustaendigeStelle xtf_char(200)
    -> UE_Ueberlagerung [UE_UeberlagerungZone]
Note: UE_UeberlagerungZoneRV
DM16NplBE_Bern.Nutzungsplanung.UE_UeberlagerungZoneRV (reader ch.ehi.fme.Main_1)
    attributes: xtf_id xtf_char(200), Typ xtf_char(200), Vorschrift xtf_char(200), ArtikelNr xtf_char(40)
    -> UE_Ueberlagerung [UE_UeberlagerungZoneRV]
UE_Ueberlagerung
    ABKUERZUNG = @Value(Abkuerzung)
    ARTIKELNR = @Value(ArtikelNr)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    INKRAFTSETZUNG = @Value(Inkraftsetzung)
    KANTART = @Value(KantArt)
    LEGEND_BASEDIR = $(LEGEND_BASEDIR)
    LEGEND_BASEURL = $(LEGEND_BASEURL)
    LEGEND_INPUTDIR = $(LEGEND_INPUTDIR)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    TYP = @Value(Typ)
    VERBINDLICHKEIT = @Value(Verbindlichkeit)
    VORSCHRIFT = @Value(Vorschrift)
    XTF_ID = @Value(xtf_id)
    ZUSTAENDIGESTELLE = @Value(ZustaendigeStelle)
    GNZPPUEO -> NUPLA_GNZPPUEO (writer GEODATABASE_SDE_2)
    GNZPPUEO -> BulkAttributeRenamer_15
    EIGENTUMSBESCHRAENKUNG -> Aggregator
    UEFL -> FeatureHolder_3
    FLAECHE -> FLAECHE (writer GEODATABASE_SDE_1)
    UELARMES -> NUPLA_UELARMES (writer GEODATABASE_SDE_2)
    UELARMES -> BulkAttributeRenamer_10
    HINVOR -> FeatureHolder
    Verwendete_Aemter -> FeatureHolder_2

Bookmark: UE_Abstandslinie
Note: UE_LinienelementAbstand
DM16NplBE_Bern.Nutzungsplanung.UE_LinienelementAbstand (reader ch.ehi.fme.Main_1)
    attributes: xtf_id xtf_char(200), Objekt xtf_char(200), Beschrieb xtf_char(80), Genehmigung xtf_date, Inkraftsetzung xtf_date, Qualitaet xtf_char(255)
    -> UE_Abstandslinie [UE_LinienelementAbstand]
Note: UE_Abstandslinie
DM16NplBE_Bern.Nutzungsplanung.UE_Abstandslinie (reader ch.ehi.fme.Main_1)
    attributes: xtf_id xtf_char(200), Verbindlichkeit xtf_char(255), KantArt xtf_char(255), Abkuerzung xtf_char(12), Bezeichnung xtf_char(150), Planbeschriftung xtf_char(150), Nutzungsziffer xtf_decimal(4,2), Nutzungsziffer_Art xtf_char(255), Gruenflaechenziffer xtf_decimal(4,2), Bemerkung xtf_char(80), DarstellungCode xtf_char(5), Datenverwaltungsstelle xtf_char(200), ZustaendigeStelle xtf_char(200), Status xtf_char(255)
    -> UE_Abstandslinie [UE_Abstandslinie]
Note: UE_AbstandslinieRV
DM16NplBE_Bern.Nutzungsplanung.UE_AbstandslinieRV (reader ch.ehi.fme.Main_1)
    attributes: xtf_id xtf_char(200), Typ xtf_char(200), Vorschrift xtf_char(200), ArtikelNr xtf_char(40)
    -> UE_Abstandslinie [UE_AbstandslinieRV]
UE_Abstandslinie
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    INKRAFTSETZUNG = @Value(Inkraftsetzung)
    KANTART = @Value(KantArt)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    STATUS = @Value(Status)
    TYP = @Value(Typ)
    UID_AMT = @Value(UID_AMT)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    UELN -> FeatureHolder_4
    UEWAABL -> NUPLA_UEWAABL (writer GEODATABASE_SDE_2)
    UEWAABL -> BulkAttributeRenamer_9
    LINIE -> LINIE (writer GEODATABASE_SDE_1)
    HINVOR -> FeatureHolder
    Verwendete_Aemter -> FeatureHolder_2

Bookmark: NH_NHSchutz
Note: NH_FlaechenelementNHS
DM16NplBE_Bern.Nutzungsplanung.NH_FlaechenelementNHS (reader ch.ehi.fme.Main_1)
    attributes: xtf_id xtf_char(200), Objekt xtf_char(200), Beschrieb xtf_char(80), Genehmigung xtf_date, Inkraftsetzung xtf_date, Qualitaet xtf_char(255)
    -> NH_NaturHeimatSchutz [NH_FlaechenelementNHS]
Note: NH_LinienelementNHS
DM16NplBE_Bern.Nutzungsplanung.NH_LinienelementNHS (reader ch.ehi.fme.Main_1)
    attributes: xtf_id xtf_char(200), Objekt xtf_char(200), Beschrieb xtf_char(80), Genehmigung xtf_date, Inkraftsetzung xtf_date, Qualitaet xtf_char(255)
    -> NH_NaturHeimatSchutz [NH_LinienelementNHS]
Note: NH_PunktelementNHS
DM16NplBE_Bern.Nutzungsplanung.NH_PunktelementNHS (reader ch.ehi.fme.Main_1)
    attributes: xtf_id xtf_char(200), Objekt xtf_char(200), Beschrieb xtf_char(80), Genehmigung xtf_date, Inkraftsetzung xtf_date, Qualitaet xtf_char(255), Ori xtf_decimal(5,1)
    -> NH_NaturHeimatSchutz [NH_PunktelementNHS]
Note: NH_NHSchutz
DM16NplBE_Bern.Nutzungsplanung.NH_NHSchutz (reader ch.ehi.fme.Main_1)
    attributes: xtf_id xtf_char(200), Verbindlichkeit xtf_char(255), KantArt xtf_char(255), Abkuerzung xtf_char(12), Bezeichnung xtf_char(150), Bedeutung xtf_char(255), Schutzgrad xtf_char(255), Planbeschriftung xtf_char(150), Bemerkung xtf_char(80), DarstellungCode xtf_char(5), Datenverwaltungsstelle xtf_char(200), ZustaendigeStelle xtf_char(200)
    -> NH_NaturHeimatSchutz [NH_NHSchutz]
Note: NH_NHSchutzRV
DM16NplBE_Bern.Nutzungsplanung.NH_NHSchutzRV (reader ch.ehi.fme.Main_1)
    attributes: xtf_id xtf_char(200), Typ xtf_char(200), Vorschrift xtf_char(200), ArtikelNr xtf_char(40)
    -> NH_NaturHeimatSchutz [NH_NHSchutzRV]
NH_NaturHeimatSchutz
    ABKUERZUNG = @Value(Abkuerzung)
    ARTIKELNR = @Value(ArtikelNr)
    BEDEUTUNG = @Value(Bedeutung)
    BEMERKUNG = @Value(Bemerkung)
    BESCHRIEB = @Value(Beschrieb)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    KANTART = @Value(KantArt)
    OBJEKT = @Value(Objekt)
    ORI = @Value(Ori)
    PLANBESCHRIFTUNG = @Value(Planbeschriftung)
    QUALITAET = @Value(Qualitaet)
    SCHUTZGRAD = @Value(Schutzgrad)
    TYP = @Value(Typ)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    UEFL -> FeatureHolder_3
    UELN -> FeatureHolder_4
    FLAECHE -> FLAECHE (writer GEODATABASE_SDE_1)
    UEPT -> NUPLA_UEPT (writer GEODATABASE_SDE_2)
    UEPT -> BulkAttributeRenamer_8
    LINIE -> LINIE (writer GEODATABASE_SDE_1)
    Verwendete_Aemter -> FeatureHolder_2
    PUNKT -> PUNKT (writer GEODATABASE_SDE_1)
    HINVOR -> FeatureHolder

Bookmark: WE_WegRoute
Note: WE_FlaechenelementWeg
DM16NplBE_Bern.Nutzungsplanung.WE_FlaechenelementWeg (reader ch.ehi.fme.Main_1)
    attributes: xtf_id xtf_char(200), Objekt xtf_char(200), Genehmigung xtf_date, Inkraftsetzung xtf_date, Qualitaet xtf_char(255)
    -> WE_WegRoute [WE_FlaechenelementWeg]
Note: WE_LinienelementWeg
DM16NplBE_Bern.Nutzungsplanung.WE_LinienelementWeg (reader ch.ehi.fme.Main_1)
    attributes: xtf_id xtf_char(200), Objekt xtf_char(200), Genehmigung xtf_date, Inkraftsetzung xtf_date, Qualitaet xtf_char(255)
    -> WE_WegRoute [WE_LinienelementWeg]
Note: WE_WegRoute
DM16NplBE_Bern.Nutzungsplanung.WE_WegRoute (reader ch.ehi.fme.Main_1)
    attributes: xtf_id xtf_char(200), Verbindlichkeit xtf_char(255), Art xtf_char(255), Bezeichnung xtf_char(150), Bedeutung xtf_char(255), Schutzgrad xtf_char(255), DarstellungCode xtf_char(5), Planbeschriftung xtf_char(150), Datenverwaltungsstelle xtf_char(200), ZustaendigeStelle xtf_char(200)
    -> WE_WegRoute [WE_WegRoute]
Note: WE_WegRouteRV
DM16NplBE_Bern.Nutzungsplanung.WE_WegRouteRV (reader ch.ehi.fme.Main_1)
    attributes: xtf_id xtf_char(200), Typ xtf_char(200), Vorschrift xtf_char(200), ArtikelNr xtf_char(40)
    -> WE_WegRoute [WE_WegRouteRV]
WE_WegRoute
    ART = @Value(Art)
    ARTIKELNR = @Value(ArtikelNr)
    BEDEUTUNG = @Value(Bedeutung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    OBJEKT = @Value(Objekt)
    PLANBESCHRIFTUNG = @Value(Planbeschriftung)
    QUALITAET = @Value(Qualitaet)
    SCHUTZGRAD = @Value(Schutzgrad)
    TYP = @Value(Typ)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    UEFL -> FeatureHolder_3
    UELN -> FeatureHolder_4
    FLAECHE -> FLAECHE (writer GEODATABASE_SDE_1)
    LINIE -> LINIE (writer GEODATABASE_SDE_1)
    Verwendete_Aemter -> FeatureHolder_2
    HINVOR -> FeatureHolder

Bookmark: GW_Gewaesser
Note: GW_FlaechenelementGew
DM16NplBE_Bern.Nutzungsplanung.GW_FlaechenelementGew (reader ch.ehi.fme.Main_1)
    attributes: xtf_id xtf_char(200), Objekt xtf_char(200), Genehmigung xtf_date, Inkraftsetzung xtf_date, Qualitaet xtf_char(255)
    -> GW_Gewaesser [GW_FlaechenelementGew]
Note: GW_LinienelementGew
DM16NplBE_Bern.Nutzungsplanung.GW_LinienelementGew (reader ch.ehi.fme.Main_1)
    attributes: xtf_id xtf_char(200), Objekt xtf_char(200), Genehmigung xtf_date, Inkraftsetzung xtf_date, Qualitaet xtf_char(255)
    -> GW_Gewaesser [GW_LinienelementGew]
Note: GW_Gewaesser
DM16NplBE_Bern.Nutzungsplanung.GW_Gewaesser (reader ch.ehi.fme.Main_1)
    attributes: xtf_id xtf_char(200), Verbindlichkeit xtf_char(255), Art xtf_char(255), Oekomorph_Natuerlichkeit xtf_char(255), Kulturhist_Bedeutung xtf_char(255), Bezeichnung xtf_char(150), Planbeschriftung xtf_char(150), Bemerkung xtf_char(80), Datenverwaltungsstelle xtf_char(200), ZustaendigeStelle xtf_char(200), DarstellungCode xtf_char(5)
    -> GW_Gewaesser [GW_Gewaesser]
Note: GW_GewaesserRV
DM16NplBE_Bern.Nutzungsplanung.GW_GewaesserRV (reader ch.ehi.fme.Main_1)
    attributes: xtf_id xtf_char(200), Typ xtf_char(200), Vorschrift xtf_char(200), ArtikelNr xtf_char(40)
    -> GW_Gewaesser [GW_GewaesserRV]
GW_Gewaesser
    ART = @Value(Art)
    ARTIKELNR = @Value(ArtikelNr)
    BEMERKUNG = @Value(Bemerkung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    KULTURHIST_BEDEUTUNG = @Value(Kulturhist_Bedeutung)
    OBJEKT = @Value(Objekt)
    OEKOMORPH_NATUERLICHKEIT = @Value(Oekomorph_Natuerlichkeit)
    PLANBESCHRIFTUNG = @Value(Planbeschriftung)
    QUALITAET = @Value(Qualitaet)
    TYP = @Value(Typ)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    UEFL -> FeatureHolder_3
    UELN -> FeatureHolder_4
    FLAECHE -> FLAECHE (writer GEODATABASE_SDE_1)
    LINIE -> LINIE (writer GEODATABASE_SDE_1)
    Verwendete_Aemter -> FeatureHolder_2
    HINVOR -> FeatureHolder

Bookmark: DARSTELLUNGSDIENST (statisch)
Note: Excel-File DARSTELLUNGSDIENST
DARSTELLUNGSDIENST (reader XLSXR_2)
    attributes: DAR_OID char(26), LAYERS char(100)
    -> StringConcatenator_4
Note: DAR_VERWEISWMS_DE
StringConcatenator_4
    PARM_LINE = $(NPL_WMS_BASE)@Value(LAYERS)
    VAL_ATTR = DAR_VERWEISWMS_DE
    -> StringConcatenator_5
Note: DAR_VERWEISWMS_FR
StringConcatenator_5
    PARM_LINE = $(NPL_WMS_BASE)@Value(LAYERS)
    VAL_ATTR = DAR_VERWEISWMS_FR
    -> StringConcatenator_6
Note: DAR_LEGENDEIMWEB_DE
StringConcatenator_6
    PARM_LINE = $(OUTPUT_RV_URL)legenden/$(BFSNR)_legende_npl_de.html
    VAL_ATTR = DAR_LEGENDEIMWEB_DE
    -> StringConcatenator_7
Note: DAR_LEGENDEIMWEB_FR
StringConcatenator_7
    PARM_LINE = $(OUTPUT_RV_URL)legenden/$(BFSNR)_legende_npl_fr.html
    VAL_ATTR = DAR_LEGENDEIMWEB_FR
    -> DARSTELLUNGSDIENST (writer ORACLE8I_DB_1)
Note: OEREB2.DARSTELLUNGSDIENST
DARSTELLUNGSDIENST (writer ORACLE8I_DB_1)
    attributes: DAR_OID nvarchar(128), DAR_XTF_ID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(6,0)

Bookmark: GR_Gewaesserraum
Note: GR_Gewaesserraumflaeche
DM16NplBE_Bern.Nutzungsplanung.GR_Gewaesserraumflaeche (reader ch.ehi.fme.Main_1)
    attributes: xtf_id xtf_char(200), Objekt xtf_char(200), Qualitaet xtf_char(255), Genehmigung xtf_date, Inkraftsetzung xtf_date
    -> GR_Gewaesserraum [GR_Gewaesserraumflaeche]
Note: GR_Gewaesserraumlinie
DM16NplBE_Bern.Nutzungsplanung.GR_Gewaesserraumlinie (reader ch.ehi.fme.Main_1)
    attributes: xtf_id xtf_char(200), Objekt xtf_char(200), AbstandLinks xtf_decimal(5,2), AbstandRechts xtf_decimal(5,2), AbstandDefinition xtf_char(255), Qualitaet xtf_char(255), Genehmigung xtf_date, Inkraftsetzung xtf_date
    -> GR_Gewaesserraum [GR_Gewaesserraumlinie]
Note: GR_Gewaesserraum
DM16NplBE_Bern.Nutzungsplanung.GR_Gewaesserraum (reader ch.ehi.fme.Main_1)
    attributes: xtf_id xtf_char(200), Verbindlichkeit xtf_char(255), Bemerkung xtf_char(80), Bezeichnung xtf_char(150), DarstellungCode xtf_char(5), Datenverwaltungsstelle xtf_char(200), ZustaendigeStelle xtf_char(200)
    -> GR_Gewaesserraum [GR_Gewaesserraum]
Note: GR_GewaesserraumRV
DM16NplBE_Bern.Nutzungsplanung.GR_GewaesserraumRV (reader ch.ehi.fme.Main_1)
    attributes: xtf_id xtf_char(200), Typ xtf_char(200), Vorschrift xtf_char(200), ArtikelNr xtf_char(40)
    -> GR_Gewaesserraum [GR_GewaesserraumRV]
GR_Gewaesserraum
    ABSTANDDEFINITION = @Value(AbstandDefinition)
    ABSTANDLINKS = @Value(AbstandLinks)
    ABSTANDRECHTS = @Value(AbstandRechts)
    ARTIKELNR = @Value(ArtikelNr)
    BEMERKUNG = @Value(Bemerkung)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    INKRAFTSETZUNG = @Value(Inkraftsetzung)
    OBJEKT = @Value(Objekt)
    QUALITAET = @Value(Qualitaet)
    TYP = @Value(Typ)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    UEFL -> FeatureHolder_3
    UELN -> FeatureHolder_4
    FLAECHE -> FLAECHE (writer GEODATABASE_SDE_1)
    LINIE -> LINIE (writer GEODATABASE_SDE_1)
    Verwendete_Aemter -> FeatureHolder_2
    HINVOR -> FeatureHolder

Bookmark: Vorübergehende Einschränkung
Note: VE_Vor_Einschraenkung
DM16NplBE_Bern.Nutzungsplanung.VE_Vor_Einschraenkung (reader ch.ehi.fme.Main_1)
    attributes: xtf_id xtf_char(200), Verbindlichkeit xtf_char(255), KantArt xtf_char(255), Gueltig_bis xtf_date, Beschwerde_haengig xtf_char(255), Abkuerzung xtf_char(12), Planbeschriftung xtf_char(150), Bezeichnung xtf_char(150), Nutzungsziffer xtf_decimal(4,2), Nutzungsziffer_Art xtf_char(255), Gruenflaechenziffer xtf_decimal(4,2), Bemerkung xtf_char(80), ThemaLaufendeAenderung xtf_char(255), DarstellungCode xtf_char(5), Datenverwaltungsstelle xtf_char(200), ZustaendigeStelle xtf_char(200)
    -> VE_Vor_Einschraenkung [VE_Vor_Einschraenkung]
Note: VE_Vor_EinschraenkungRV
DM16NplBE_Bern.Nutzungsplanung.VE_Vor_EinschraenkungRV (reader ch.ehi.fme.Main_1)
    attributes: xtf_id xtf_char(200), Typ xtf_char(200), Vorschrift xtf_char(200), ArtikelNr xtf_char(40)
    -> VE_Vor_Einschraenkung [VE_Vor_EinschraenkungRV]
Note: VE_FlaechenelementEinschr
DM16NplBE_Bern.Nutzungsplanung.VE_FlaechenelementEinschr (reader ch.ehi.fme.Main_1)
    attributes: xtf_id xtf_char(200), Objekt xtf_char(200), Genehmigung xtf_date, Inkraftsetzung xtf_date, Beschrieb xtf_char(80), Qualitaet xtf_char(255)
    -> VE_Vor_Einschraenkung [VE_FlaechenelementEinschr]
VE_Vor_Einschraenkung
    ABKUERZUNG = @Value(Abkuerzung)
    AMTIMWEB = @Value(AMTIMWEB)
    AMTNAME = @Value(AMTNAME)
    AMT_ID = @Value(AMT_ID)
    AMT_XTF_ID = @Value(AMT_XTF_ID)
    ARTIKELNR = @Value(ArtikelNr)
    BEMERKUNG = @Value(Bemerkung)
    BESCHRIEB = @Value(Beschrieb)
    BESCHWERDE_HAENGIG = @Value(Beschwerde_haengig)
    BEZEICHNUNG = @Value(Bezeichnung)
    BFSNR = $(BFSNR)
    DARSTELLUNGCODE = @Value(DarstellungCode)
    DATENVERWALTUNGSSTELLE = @Value(Datenverwaltungsstelle)
    GENEHMIGUNG = @Value(Genehmigung)
    GEODB_DATABASE = $(GEODB_DATABASE)
    GEODB_PASSWORD = $(GEODB_PASSWORD)
    GEODB_USERNAME = $(GEODB_USERNAME)
    GRUENFLAECHENZIFFER = @Value(Gruenflaechenziffer)
    GUELTIG_BIS = @Value(Gueltig_bis)
    INKRAFTSETZUNG = @Value(Inkraftsetzung)
    KANTART = @Value(KantArt)
    NUTZUNGSZIFFER = @Value(Nutzungsziffer)
    NUTZUNGSZIFFER_ART = @Value(Nutzungsziffer_Art)
    OBJEKT = @Value(Objekt)
    PLANBESCHRIFTUNG = @Value(Planbeschriftung)
    QUALITAET = @Value(Qualitaet)
    THEMALAUFENDEAENDERUNG = @Value(ThemaLaufendeAenderung)
    TYP = @Value(Typ)
    UID_AMT = @Value(UID_AMT)
    VERBINDLICHKEIT = @Value(Verbindlichkeit)
    VORSCHRIFT = @Value(Vorschrift)
    XTF_ID = @Value(xtf_id)
    ZUSTAENDIGESTELLE = @Value(ZustaendigeStelle)
    EIGENTUMSBESCHRAENKUNG -> Aggregator
    FLAECHE -> FLAECHE (writer GEODATABASE_SDE_1)
    UEFL -> FeatureHolder_3
    HINVOR -> FeatureHolder
    VerwendeteAemter -> FeatureHolder_2

Bookmark: Dokumente / Amt
Note: Amt
DM16NplBE_Bern.Nutzungsplanung.Amt (reader ch.ehi.fme.Main_1)
    attributes: xtf_id xtf_char(200), Name xtf_char(200), UID_Amt xtf_char(15), AmtImWeb xtf_char(200)
    -> Amt_vorbereiten [Amt]
Note: Dokument
DM16NplBE_Bern.Nutzungsplanung.Dokument (reader ch.ehi.fme.Main_1)
    attributes: xtf_id xtf_char(200), Art_Doku xtf_char(255), Titel xtf_char(200), OffiziellerTitel xtf_char(200), Abkuerzung xtf_char(20), OffizielleNr xtf_char(20), Gemeinde xtf_int32, Dokument xtf_char(100), ZustaendigeStelle xtf_char(200)
    -> Dokument_vorbereiten [Dokument]
Note: HinweisWeitereDokumente
DM16NplBE_Bern.Nutzungsplanung.HinweisWeitereDokumente (reader ch.ehi.fme.Main_1)
    attributes: xtf_id xtf_char(200), Ursprung xtf_char(200), Hinweis xtf_char(200), ArtikelNr xtf_char(40), Ordnungsnummer xtf_int32
    -> HINWEIDOK-IDs_ersetzen [HinweisWeitereDokumente]

Bookmark: Gesetzliche Grundagen statisch verlinken (gemäss Handbuch DM16)
Note: Lärmschutzverordnung Bund als GEGR
AttributeCreator_9
    ATTR_LIST = VOR_OID,ch.admin.bk.sr.814.41
    -> UUIDGenerator_6
Note: Waldgesetz Bund als GEGR
AttributeCreator
    ATTR_LIST = VOR_OID,ch.admin.bk.sr.921.0
    -> UUIDGenerator_6
Note: Waldgesetz Kanton als GEGR
AttributeCreator_3
    ATTR_LIST = VOR_OID,ch.be.sk.bsg.921.11
    -> UUIDGenerator_6
Note: Waldverordnung Kanton als GEGR
AttributeCreator_4
    ATTR_LIST = VOR_OID,ch.be.sk.bsg.921.111
    -> UUIDGenerator_6
Note: Raumplanungsgesetz als GEGR
AttributeCreator_5
    ATTR_LIST = VOR_OID,ch.admin.bk.sr.700
    -> UUIDGenerator_6
Note: Baugesetz als GEGR
AttributeCreator_6
    ATTR_LIST = VOR_OID,ch.be.sk.bsg.721.0
    -> UUIDGenerator_6
Note: Bauverordnung als GEGR
AttributeCreator_7
    ATTR_LIST = VOR_OID,ch.be.sk.bsg.721.1
    -> UUIDGenerator_6
Note: BMBV als GEGR
AttributeCreator_8
    ATTR_LIST = VOR_OID,ch.be.sk.bsg.721.3
    -> UUIDGenerator_6
Note: HIV_ID
UUIDGenerator_6
    UUID_ATTR = HIV_ID
    -> AttributeRemover_17
AttributeRemover_17
    REMOVE_ATTRS = EIB_XTF_ID,STH_ID
    -> HINVOR (writer ORACLE8I_DB_1)
    -> AttributeRemover_19

Bookmark: Wertetabellen (sind bereits vorabgefüllt)
Note: NUPLA_VETHEMAT
NUPLA_VETHEMAT (writer GEODATABASE_SDE_2) [off]
    attributes: geodb_oid integer, OBJECTID integer, VE_THEMA smallint, BEZ_DE char(100), BEZ_FR char(100)
Note: NUPLA_VERBINDT
NUPLA_VERBINDT (writer GEODATABASE_SDE_2) [off]
    attributes: geodb_oid integer, OBJECTID integer, VERBINDLKT smallint, BEZ_DE char(100), BEZ_FR char(100)
Note: NUPLA_UEARTKTT
NUPLA_UEARTKTT (writer GEODATABASE_SDE_2) [off]
    attributes: geodb_oid integer, OBJECTID integer, KANTART smallint, BEZ_DE char(100), BEZ_FR char(100)
Note: NUPLA_GWBDBEST
NUPLA_GWBDBEST (writer GEODATABASE_SDE_2) [off]
    attributes: geodb_oid integer, OBJECTID integer, CODE smallint, BEZ_DE char(100), BEZ_FR char(100)
Note: NUPLA_ABSTDEFT
NUPLA_ABSTDEFT (writer GEODATABASE_SDE_2) [off]
    attributes: geodb_oid integer, OBJECTID integer, ABSTDEF smallint, BEZ_DE char(100), BEZ_FR char(100)
Note: NUPLA_STATUST
NUPLA_STATUST (writer GEODATABASE_SDE_2) [off]
    attributes: geodb_oid integer, OBJECTID integer, STATUS smallint, BEZ_DE char(100), BEZ_FR char(100)
Note: NUPLA_SCHUTZGT
NUPLA_SCHUTZGT (writer GEODATABASE_SDE_2) [off]
    attributes: geodb_oid integer, OBJECTID integer, SCHUTZG smallint, BEZ_DE char(100), BEZ_FR char(100)
Note: NUPLA_QUALIT
NUPLA_QUALIT (writer GEODATABASE_SDE_2) [off]
    attributes: geodb_oid integer, OBJECTID integer, QUALITAET smallint, BEZ_DE char(100), BEZ_FR char(100)
Note: NUPLA_BUNDESAT
NUPLA_BUNDESAT (writer GEODATABASE_SDE_2) [off]
    attributes: geodb_oid integer, OBJECTID integer, BUNDESART char(10), BEZ_DE char(150), BEZ_FR char(150)
Note: NUPLA_UNBET
NUPLA_UNBET (writer GEODATABASE_SDE_2) [off]
    attributes: geodb_oid integer, OBJECTID integer, UNBESCHR smallint, BEZ_DE char(100), BEZ_FR char(100)
Note: NUPLA_NZARTT
NUPLA_NZARTT (writer GEODATABASE_SDE_2) [off]
    attributes: geodb_oid integer, OBJECTID integer, NZ_ART smallint, BEZ_DE char(100), BEZ_FR char(100)
Note: NUPLA_NPZONET
NUPLA_NPZONET (writer GEODATABASE_SDE_2) [off]
    attributes: geodb_oid integer, OBJECTID integer, KANTART char(10), BEZ_DE char(100), BEZ_FR char(100)
Note: NUPLA_GWNATT
NUPLA_GWNATT (writer GEODATABASE_SDE_2) [off]
    attributes: geodb_oid integer, OBJECTID integer, GW_NAT smallint, BEZ_DE char(100), BEZ_FR char(100)
Note: NUPLA_BEDEUTT
NUPLA_BEDEUTT (writer GEODATABASE_SDE_2) [off]
    attributes: geodb_oid integer, OBJECTID integer, BEDEUT smallint, BEZ_DE char(100), BEZ_FR char(100)
Note: NUPLA_BWTYPT
NUPLA_BWTYPT (writer GEODATABASE_SDE_2) [off]
    attributes: geodb_oid integer, OBJECTID integer, BWTYP smallint, BEZ_DE char(100), BEZ_FR char(100)

Bookmark: AMT
Note: AMT (Excel)
AMT (reader XLSXR_1)
    attributes: AMT_OID char(18), AMT_NAME_DE char(17), AMT_NAME_FR char(17), AMT_AMTIMWEB_DE char(22), AMT_AMTIMWEB_FR char(22)
    -> AMT (writer ORACLE8I_DB_1)
Note: OEREB2.AMT
AMT (writer ORACLE8I_DB_1)
    attributes: AMT_OID nvarchar(128), AMT_XTF_ID nvarchar(128), AMT_NAME_DE nvarchar(255), AMT_NAME_FR nvarchar(255), AMT_AMTIMWEB_DE nvarchar(1023), AMT_AMTIMWEB_FR nvarchar(1023), AMT_LIEFEREINHEIT number(6,0), AMT_LINE1 nvarchar(80), AMT_LINE2 nvarchar(80), AMT_STREET nvarchar(100), AMT_NUMBER nvarchar(7), AMT_POSTALCODE nvarchar(4), AMT_CITY nvarchar(60)

Bookmark: In der Stadt Bern nicht verwendet
Note: NUPLA_GNGRUZO
NUPLA_GNGRUZO (writer GEODATABASE_SDE_2) [off]
    attributes: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

Bookmark: Deaktiviert, da in diesem Fall nie abgefüllt
Note: OEREB2.ARTIKEL
ARTIKEL (writer ORACLE8I_DB_1) [off]
    attributes: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
Note: OEREB2.HINWEIDOK
HINWEIDOK (writer ORACLE8I_DB_1) [off]
    attributes: HWD_ID nvarchar(128), HWD_XTF_ID nvarchar(128), HWD_LIEFEREINHEIT number(6,0), HWD_ARTNR nvarchar(255), VOR_OIDURSPRUNG nvarchar(128), VOR_OIDHINWEIS nvarchar(128)

FME custom transformer HINWEIDOK-IDs ersetzen

Parameters:
- ARTIKELNR = @Value(ArtikelNr)   # ArtikelNr
- ORDNUNGSNUMMER = @Value(Ordnungsnummer)   # Ordnungsnummer
- VOR_OID = @Value(VOR_OID)   # Vor Oid
- URSPRUNG = @Value(Ursprung)   # Ursprung
- HINWEIS = @Value(Hinweis)   # Hinweis
- VOR_XTF_ID = @Value(VOR_XTF_ID)   # Vor Xtf Id

AlleDokumente (input)
    -> AttributeRemover_9
AttributeRemover_9
    REMOVE_ATTRS = Art_Doku,VOR_TITEL_DE,VOR_OFFIZIELLERTITEL_DE,VOR_ABKUERZUNG_DE,VOR_OFFIZIELLENR,Gemeinde,Dokument,ZustaendigeStelle,VOR_PUBLIZIERTAB,VOA_ID,VOR_TITEL_FR,VOR_OFFIZIELLERTITEL_FR,VOR_ABKUERZUNG_FR,VOR_TEXTIMWEB_DE,VOR_TEXTIMWEB_FR,filecopy_source_dataset,filecopy_dest_dataset
    -> FeatureMerger_5 [SUPPLIER]
    -> FeatureMerger_6 [SUPPLIER]
HinweisWeitereDokumente (input)
    -> AttributeRenamer_5
AttributeRenamer_5
    ATTR_LIST = ArtikelNr,ARTIKELNR,"",Ordnungsnummer,ORDNNR,""
    -> AttributeRemover_7
AttributeRemover_7
    REMOVE_ATTRS = xtf_id
    -> FeatureMerger_5 [REQUESTOR]
FeatureMerger_5
    IGNORE_NULLS = Yes
    JOIN_KEYS = @Value(Ursprung) @Value(VOR_XTF_ID) AUTO
    MERGE_TYPE = Attributes Only
    PROCESS_DUPS = No
    SUPPLIERS_FIRST = No
    SUPPLIER_PREFIX_DUMMY = YES
    MERGED -> AttributeRenamer_6
AttributeRenamer_6
    ATTR_LIST = VOR_OID,VOR_OIDURSPRUNG,""
    -> AttributeRemover_12
AttributeRemover_12
    REMOVE_ATTRS = Ursprung,VOR_XTF_ID
    -> FeatureMerger_6 [REQUESTOR]
FeatureMerger_6
    IGNORE_NULLS = Yes
    JOIN_KEYS = @Value(Hinweis) @Value(VOR_XTF_ID) AUTO
    MERGE_TYPE = Attributes Only
    PROCESS_DUPS = No
    SUPPLIERS_FIRST = No
    SUPPLIER_PREFIX_DUMMY = YES
    MERGED -> AttributeRenamer_8
AttributeRenamer_8
    ATTR_LIST = VOR_OID,VOR_OIDHINWEIS,""
    -> AttributeRemover_13
AttributeRemover_13
    REMOVE_ATTRS = Hinweis,VOR_XTF_ID
    -> HINWEIDOK_ID_ersetzt (output)
HINWEIDOK_ID_ersetzt (output)

FME custom transformer GN_Bauweise

Parameters:
- BFSNR =   # BFS-Nummer
- GEBAEUDETIEFE = @Value(Gebaeudetiefe)   # Gebaeudetiefe
- XTF_ID = @Value(xtf_id)   # Xtf Id
- TYPOLOGIE = @Value(Typologie)   # Typologie
- ARTIKELNR = @Value(ArtikelNr)   # ArtikelNr
- INKRAFTSETZUNG = @Value(Inkraftsetzung)   # Inkraftsetzung
- DARSTELLUNGCODE = @Value(DarstellungCode)   # DarstellungCode
- QUALITAET = @Value(Qualitaet)   # Qualitaet
- GEBAEUDETIEFE_UNBESCHRAENKT = @Value(Gebaeudetiefe_unbeschraenkt)   # Gebaeudetiefe Unbeschraenkt
- GEBAEUDELAENGE = @Value(Gebaeudelaenge)   # Gebaeudelaenge
- GEBAEUDELAENGE_UNBESCHRAENKT = @Value(Gebaeudelaenge_unbeschraenkt)   # Gebaeudelaenge Unbeschraenkt
- TYP = @Value(Typ)   # Typ
- GENEHMIGUNG = @Value(Genehmigung)   # Genehmigung
- LEGEND_BASEURL =
- LEGEND_BASEDIR =
- LEGEND_INPUTDIR =
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- VORSCHRIFT = @Value(Vorschrift)   # Vorschrift
- DATENVERWALTUNGSSTELLE = @Value(Datenverwaltungsstelle)   # Datenverwaltungsstelle
- ZUSTAENDIGESTELLE = @Value(ZustaendigeStelle)   # ZustaendigeStelle
- GEODB_DATABASE =
- GEODB_USERNAME =
- GEODB_PASSWORD =

GN_Bauweise (input)
    -> AttributeKeeper_8
AttributeKeeper_8
    KEEP_ATTRS = Gebaeudetiefe,xtf_id,Typologie,Inkraftsetzung,DarstellungCode,Qualitaet,Gebaeudetiefe_unbeschraenkt,Gebaeudelaenge,Gebaeudelaenge_unbeschraenkt,Genehmigung,Datenverwaltungsstelle,ZustaendigeStelle
    -> UUIDGenerator
Note: EIB_OID
UUIDGenerator
    UUID_ATTR = EIB_OID
    -> AttributeRenamer
AttributeRenamer
    ATTR_LIST = xtf_id,EIB_XTF_ID,""
    -> UUIDGenerator_2
Note: FLA_OID
UUIDGenerator_2
    UUID_ATTR = FLA_OID
    -> TimeStamper
TimeStamper
    FMT = FME Date (^Y^m^d)
    TIME_ATTR = EIB_PUBLIZIERTAB
    -> AttributeRenamer_2
AttributeRenamer_2
    ATTR_LIST = DarstellungCode,DARST_C,"",Genehmigung,GENEHM,"",Inkraftsetzung,INKRAFT,"",Gebaeudelaenge,GEBL,"",Gebaeudetiefe,GEBT,"",Datenverwaltungsstelle,DATENVERW,"",ZustaendigeStelle,ZUSTAENDIG,""
    -> DateFormatter
DateFormatter
    DATE_ATTR = GENEHM,INKRAFT
    FMT = FME Date (%Y%m%d)
    INVALID_DATE_VALUE = _FME_NO_OP_
    SRCFMT = Unknown - Automatic Detection
    -> AttributeCreator_11
AttributeCreator_11
    ATTR_LIST = RVS_ID,@Value(EIB_OID),EIB_SORT,155,RES_ID,1,STH_ID,17,FLA_PUBLIZIERTAB,@Value(EIB_PUBLIZIERTAB),DAR_OID,ch.be.bve.agi.npl.$(BFSNR).17
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper
Note: BWTYP mappen / Interlis-Codelisten starten bei 0, / GeoDB-Wertetabellen bei 1!
AttributeValueMapper
    DIRECTION = Forward (Source To Destination)
    LUT = 0,1,1,2,2,3
    SRC = Typologie
    VAL_ATTR = BWTYP
    -> Joiner
Note: BAUWEISE mappen (wird für / EIB_AISSAGE_DE gebraucht)
Joiner
    ADDED_FIELDS = BEZ_DE
    CACHE_SIZE = 5000
    DATASET = $(GEODB_DATABASE)
    FORMAT = ORACLE8I_DB
    JOIN_KEYS = BWTYP BWTYP
    MATCH_RULE_DISPLAY = Must Match Exactly One (1:1)
    ORACLE8I_DB_PASSWORD = $(GEODB_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    ORACLE8I_DB_USE_UNIFIED_DATE_ATTRS = YES
    PREFETCH_EXHAUSTIVE = Yes
    TABLE = GEODB.NUPLA_BWTYPT
    JOINED -> AttributeRenamer_4
AttributeRenamer_4
    ATTR_LIST = BEZ_DE,BAUWEISE,""
    -> AttributeValueMapper_2
Note: GEBLU mappen / Interlis-Codelisten starten bei 0, / GeoDB-Wertetabellen bei 1!
AttributeValueMapper_2
    DIRECTION = Forward (Source To Destination)
    LUT = 0,1,1,2
    SRC = Gebaeudelaenge_unbeschraenkt
    VAL_ATTR = GEBLU
    -> AttributeValueMapper_4
Note: GEBLT mappen / Interlis-Codelisten starten bei 0, / GeoDB-Wertetabellen bei 1!
AttributeValueMapper_4
    DIRECTION = Forward (Source To Destination)
    LUT = 0,1,1,2
    SRC = Gebaeudetiefe_unbeschraenkt
    VAL_ATTR = GEBTU
    -> PythonCaller_2
Note: Legendenbilder
PythonCaller_2
    NEW_ATTRIBUTES = EIB_LEGENDESYMBOL_DE EIB_LEGENDESYMBOL_FR filecopy_source_dataset filecopy_dest_dataset
    PYTHONSOURCE:
      import fmeobjects
      import os

      def processFeature(feature):

          bauweise = feature.getAttribute("BWTYP")

          filename = 'bw_offen.png'

          if bauweise == "1":
              filename = "bw_offen.png"
          elif bauweise == "2":
              filename = "bw_geschl.png"
          elif bauweise == "3":
              filename = "bw_offen.png"

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> PythonCaller
Note: EIB_AUSSAGE_DE
PythonCaller
    NEW_ATTRIBUTES = EIB_AUSSAGE_DE EIB_AUSSAGE_FR GEBLSYM GEBTSYM
    PYTHONSOURCE:
      import fmeobjects

      def getAussageBW(feature):
          aussage = ""
          bauweise = feature.getAttribute("BAUWEISE")
          gebtiefe = feature.getAttribute("GEBT")
          gebtiefunb = feature.getAttribute("GEBTU")
          geblaenge = feature.getAttribute("GEBL")
          geblangunb = feature.getAttribute("GEBLU")

          # zuerst Symbole berechnen (Entweder "", Unendlichkeit oder Zahl)
          geblangsym = ""
          if geblangunb is not None and geblangunb != "":
              geblangsym = u"\u221E"
          elif geblaenge is not None and geblaenge != "":
              geblangsym = str(geblaenge)

          gebtiefsym = ""
          if gebtiefunb is not None and gebtiefunb != "":
              gebtiefsym = u"\u221E"
          elif gebtiefe is not None and gebtiefe != "":
              gebtiefsym = str(gebtiefe)

          if bauweise is not None and bauweise != "": # Nur wenn bauweise abgefüllt, wird der Rest ausgewertet
              aussage = aussage + "Bauweise " + bauweise
              if geblangsym == "" and gebtiefsym == "":
                  aussage = aussage + ", max. Gebaeudelaenge/-tiefe [m] = keine"
              else:
                  aussage = aussage + ", max. Gebaeudelaenge/-tiefe [m] = " + geblangsym + " / " + gebtiefsym
          else:
              aussage = aussage + "Bauweise keine"

          feature.setAttribute("EIB_AUSSAGE_DE", aussage)
          feature.setAttribute("EIB_AUSSAGE_FR", aussage)
          feature.setAttribute("GEBLSYM", geblangsym)
          feature.setAttribute("GEBTSYM", gebtiefsym)
    PYTHONSYMBOL = getAussageBW
    -> InlineQuerier [ZONE]
AlleÄmter (input)
    -> AttributeKeeper_6
AttributeKeeper_6
    KEEP_ATTRS = AMT_XTF_ID,AMTNAME,UID_AMT,AMTIMWEB,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeKeeper
    JOIN -> AttributeRemover_4
    JOIN -> AttributeKeeper_5
AttributeRemover_4
    REMOVE_ATTRS = xtf_id,Qualitaet,Datenverwaltungsstelle,ZustaendigeStelle,Gebaeudelaenge_unbeschraenkt,Gebaeudetiefe_unbeschraenkt,Typologie
    -> AttributeKeeper_2
    -> AttributeKeeper_3
    -> AttributeKeeper_7
AttributeKeeper_2
    KEEP_ATTRS = EIB_XTF_ID,EIB_OID,EIB_PUBLIZIERTAB,EIB_SORT,RES_ID,STH_ID,DAR_OID,EIB_LEGENDESYMBOL_DE,EIB_LEGENDESYMBOL_FR,filecopy_source_dataset,filecopy_dest_dataset,EIB_AUSSAGE_DE,EIB_AUSSAGE_FR
    -> EIGENTUMSBESCHRAENKUNG (output)
EIGENTUMSBESCHRAENKUNG (output)
AttributeKeeper_3
    KEEP_ATTRS = DATENVERW,ZUSTAENDIG,GEBL,GEBT,GENEHM,INKRAFT,DARST_C,RVS_ID,QUALITAET,BWTYP,GEBLU,GEBTU,GEBLSYM,GEBTSYM
    -> GN_BAUWS (output)
GN_BAUWS (output)
AttributeKeeper_7
    KEEP_ATTRS = EIB_OID,FLA_OID,RES_ID,FLA_PUBLIZIERTAB
    -> FLAECHE (output)
FLAECHE (output)
AttributeKeeper
    KEEP_ATTRS = DATENVERW,ZUSTAENDIG
    -> Aggregator_4
Aggregator_4
    ACCUM_ATTRS_NAME = Yes
    GROUP_BY = DATENVERW ZUSTAENDIG
    MODE = Attributes Only
    ORDERED = No
    SEP = ,
    AGGREGATE -> VerwendeteÄmter (output)
VerwendeteÄmter (output)
AttributeKeeper_5
    KEEP_ATTRS = EIB_XTF_ID,EIB_OID
    -> FeatureMerger [SUPPLIER]
GN_BauweiseRV (input)
    -> AttributeKeeper_4
AttributeKeeper_4
    KEEP_ATTRS = Typ,Vorschrift,ArtikelNr
    -> AttributeRenamer_3
AttributeRenamer_3
    ATTR_LIST = ArtikelNr,HIV_ARTNR,""
    -> FeatureMerger [REQUESTOR]
FeatureMerger
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeRemover_5
AttributeRemover_5
    REMOVE_ATTRS = Typ
    -> HINVOR (output)
HINVOR (output)

FME custom transformer GN_ZPPUEO

Parameters:
- GEODB_DATABASE =   # GeoDB-Database
- GEODB_USERNAME =   # GeoDB-Username
- GEODB_PASSWORD =   # GeoDB-Passwort
- BFSNR =   # BFS-Nummer
- RV_XTF_ID = @Value(rv_xtf_id)   # Rv Xtf Id
- RV_TYP = @Value(rv_Typ)   # Rv Typ
- RV_VORSCHRIFT = @Value(rv_Vorschrift)   # Rv Vorschrift
- RV_ARTIKELNR = @Value(rv_ArtikelNr)   # Rv Artikelnr
- ZT_XTF_ID = @Value(zt_xtf_id)   # Zt Xtf Id
- ZT_VERBINDLICHKEIT = @Value(zt_Verbindlichkeit)   # Zt Verbindlichkeit
- ZT_KANTART = @Value(zt_KantArt)   # Zt Kantart
- ZT_ABKUERZUNG = @Value(zt_Abkuerzung)   # Zt Abkuerzung
- ZT_BEZEICHNUNG = @Value(zt_Bezeichnung)   # Zt Bezeichnung
- ZT_BR_NUTZUNGSART = @Value(zt_BR_Nutzungsart)   # Zt Br Nutzungsart
- ZT_BR_NUTZUNGSMASS = @Value(zt_BR_Nutzungsmass)   # Zt Br Nutzungsmass
- ZT_NUTZUNGSZIFFER = @Value(zt_Nutzungsziffer)   # Zt Nutzungsziffer
- ZT_NUTZUNGSZIFFER_ART = @Value(zt_Nutzungsziffer_Art)   # Zt Nutzungsziffer Art
- ZT_GRUENFLAECHENZIFFER = @Value(zt_Gruenflaechenziffer)   # Zt Gruenflaechenziffer
- ZT_BEMERKUNG = @Value(zt_Bemerkung)   # Zt Bemerkung
- ZT_DATENVERWALTUNGSSTELLE = @Value(zt_Datenverwaltungsstelle)   # Zt Datenverwaltungsstelle
- ZT_ZUSTAENDIGESTELLE = @Value(zt_ZustaendigeStelle)   # Zt Zustaendigestelle
- ZT_NUTZUNGSZONE = @Value(zt_Nutzungszone)   # Zt Nutzungszone
- ZT_DARSTELLUNGCODENZ = @Value(zt_DarstellungCodeNZ)   # Zt Darstellungcodenz
- ZT_BAUKLASSE = @Value(zt_Bauklasse)   # Zt Bauklasse
- ZT_DARSTELLUNGCODEBK = @Value(zt_DarstellungCodeBK)   # Zt Darstellungcodebk
- ZPP_XTF_ID = @Value(zpp_xtf_id)   # Zpp Xtf Id
- ZPP_ZONENTYPREF = @Value(zpp_ZonentypRef)   # Zpp Zonentypref
- ZPP_GENEHMIGUNG = @Value(zpp_Genehmigung)   # Zpp Genehmigung
- ZPP_INKRAFTSETZUNG = @Value(zpp_Inkraftsetzung)   # Zpp Inkraftsetzung
- ZPP_LAERMEMPFINDLICHKEIT = @Value(zpp_Laermempfindlichkeit)   # Zpp Laermempfindlichkeit
- ZPP_BESCHRIEB = @Value(zpp_Beschrieb)   # Zpp Beschrieb
- ZPP_PLANBESCHRIFTUNG = @Value(zpp_Planbeschriftung)   # Zpp Planbeschriftung
- ZPP_QUALITAET = @Value(zpp_Qualitaet)   # Zpp Qualitaet
- ZPP_BEMERKUNG = @Value(zpp_Bemerkung)   # Zpp Bemerkung
- ZPP_FLAECHENMASS = @Value(zpp_Flaechenmass)   # Zpp Flaechenmass
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id

GN_GrundzoneZPP_UeO (input)
    -> AttributeKeeper_2
AttributeKeeper_2
    KEEP_ATTRS = zpp_xtf_id,zpp_ZonentypRef,zpp_Genehmigung,zpp_Inkraftsetzung,zpp_Laermempfindlichkeit,zpp_Beschrieb,zpp_Planbeschriftung,zpp_Qualitaet,zpp_Bemerkung,zpp_Flaechenmass
    -> UUIDGenerator_2
Note: FLA_OID
UUIDGenerator_2
    UUID_ATTR = FLA_OID
    -> AttributeRenamer_5
AttributeRenamer_5
    ATTR_LIST = zpp_xtf_id,FLA_XTF_ID,""
    -> FeatureMerger [REQUESTOR]
GN_Zonentyp (input)
    -> AttributeKeeper_3
AttributeKeeper_3
    KEEP_ATTRS = zt_xtf_id,zt_Verbindlichkeit,zt_KantArt,zt_Abkuerzung,zt_Bezeichnung,zt_BR_Nutzungsart,zt_BR_Nutzungsmass,zt_Nutzungsziffer,zt_Nutzungsziffer_Art,zt_Gruenflaechenziffer,zt_Bemerkung,zt_Datenverwaltungsstelle,zt_ZustaendigeStelle,zt_Nutzungszone,zt_DarstellungCodeNZ,zt_Bauklasse,zt_DarstellungCodeBK
    -> UUIDGenerator
Note: EIB_OID
UUIDGenerator
    UUID_ATTR = EIB_OID
    -> AttributeRenamer
AttributeRenamer
    ATTR_LIST = zt_xtf_id,EIB_XTF_ID,""
    -> AttributeFilter
Note: Nach Festlegung Gemeinde / und Hinweise filtern
AttributeFilter
    ATTR_NAME = zt_Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(zpp_ZonentypRef) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = zpp_Genehmigung,GENEHM,"",zpp_Genehmigung,INKRAFT,"",zpp_Beschrieb,BESCHRIEB,"",zt_Bezeichnung,BEZ,"",zpp_Planbeschriftung,PLANBESCHR,"",zt_Bemerkung,BEMERK,"",zt_Abkuerzung,ZONENABK,"",zt_DarstellungCodeBK,DARST_C_BK,"",zt_BR_Nutzungsart,BR_NUTZART,"",zt_BR_Nutzungsmass,BR_NMASS,"",zt_Nutzungsziffer,NZ,"",zt_Gruenflaechenziffer,GRUENFZ,"",zpp_Flaechenmass,FLMASS,"",zt_Datenverwaltungsstelle,DATENVERW,"",zt_ZustaendigeStelle,ZUSTAENDIG,"",zt_DarstellungCodeNZ,DARST_C,""
    -> AttributeCreator
AttributeCreator
    ATTR_LIST = RVS_ID,@Value(EIB_OID),EIB_ARTCODE,@Value(ZONENABK),EIB_SORT,@Evaluate(100+@int(@Value(zt_Nutzungszone))),RES_ID,1,STH_ID,16,FLA_PUBLIZIERTAB,@Value(EIB_PUBLIZIERTAB),DAR_OID,ch.be.bve.agi.npl.$(BFSNR).16
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = zpp_Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = zt_Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = zt_Nutzungsziffer_Art
    VAL_ATTR = NZ_ART
    -> AttributeValueMapper
Note: LAERMES mappen. / Inerlis-Codeliste startet bei 0, / die GeoDB-Wertetabelle hier / bei 7 (UEARTKTT)
AttributeValueMapper
    DIRECTION = Forward (Source To Destination)
    LUT = 0,7,1,8,2,9,3,10,4,11,5,12
    SRC = zpp_Laermempfindlichkeit
    VAL_ATTR = LAERMES
    -> AttributeValueMapper_5
Note: KANTART mappen. / Interlis-Codelisten starten bei 0, / GeoDB-Wertetabellen bei 1! / Achtung: Bern hat zwei zusätliche / Werte!!!
AttributeValueMapper_5
    DIRECTION = Forward (Source To Destination)
    LUT = 0,W1,1,W2,2,W3,3,W4,4,W5,5,W6plus,6,WE,7,FH,8,M2,9,M3,10,M4,11,M5,12,M6plus,13,ME,14,KS,15,KL,16,HT,17,WEZ,18,B_E,19,BH,20,A,21,ZOEN,22,SKI,23,ZSF,24,GR,25,GB,26,LWZ,27,ILW,28,AA,29,ZMN,30,UEO,31,ZPP,32,SBV,33,USP,34,Uebrige
    SRC = zt_KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_NPZONET
    JOINED -> AttributeValueMapper_23
Note: NZ_TYP mappen.
AttributeValueMapper_23
    DIRECTION = Forward (Source To Destination)
    LUT = 0,unbekannt,1,Wohnzone (W),10,Freifläche A* (Zone für priv. Bauten + Anl. im allg. Int. FA*),11,Freifläche B* (Zone für priv. Bauten + Anl. im allg. Int. FB*),12,Freifläche C* (Zone für priv. Bauten + Anl. im allg. Int. FC*),13,Freifläche D* (Zone für priv. Bauten + Anl. im allg. Int. FD*),14,Schutzzone A (SZA) Landschafts- + Ortsbildschutzareal,15,Schutzzone B (SZB) Landschafts- + Ortsbildschutzareal,16,Schutzzone C (SZC) Naturschutzareal,17,Obere Altstadt, Zone mit Planungspflicht,18,Untere Altstadt und Wohngebiet Matte,19,Gewerbegebiete Matte, Zone mit Planungspflicht,2,Gemischte Wohnzone (WG),20,Landwirtschaftszone,21,Weilerzone,22,Übriges Gebiet: Wald,23,Übriges Gebiet: Gewässer,24,Übriges Gebiet: Verkehrsfläche ausserhalb Siedlungsgebiet,25,Überbauungsordnung,26,Zone mit Planungspflicht,27,Übriges Gebiet: andere,3,Kernzone (K),4,Dienstleistungszone (D),5,Industrie- und Gewerbezone (IG),6,Freifläche A (Zone für öff. Nutzungen FA),7,Freifläche B (Zone für öff. Nutzungen FB),8,Freifläche C (Zone für öff. Nutzungen FC),9,Freifläche D (Zone für öff. Nutzungen FD)
    SRC = zt_Nutzungszone
    VAL_ATTR = NZ_TYP
    -> AttributeValueMapper_22
Note: BK_TYP mappen
AttributeValueMapper_22
    DIRECTION = Forward (Source To Destination)
    LUT = 0,unbekannt,1,Bauklasse 1,10,Obere Altstadt, Zone mit Planungspflicht,11,Untere Altstadt und Wohngebiet Matte,12,Gewerbegebiete Matte, Zone mit Planungspflicht,13,Landwirtschaftszone,14,Weilerzone,15,Übriges Gebiet: Wald,16,Übriges Gebiet: Gewässer,17,Übriges Gebiet: Verkehrsanlagen,18,Überbauungsordnung,19,Zone mit Planungspflicht,20,Übriges Gebiet: andere,2,Bauklasse 2,3,Bauklasse 3,4,Bauklasse 4,5,Bauklasse 5,6,Bauklasse 6,7,Bauklasse E, Erhaltung der best. Bebauungsstruktur,8,Festlegung der Bebauung mittels spezieller Vorschriften,9,Zone im öffentlichen Interesse
    SRC = zt_Bauklasse
    VAL_ATTR = BK_TYP
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          nz = feature.getAttribute('zt_Nutzungszone')
          filename = 'nozppueo.png'
          if nz == '25':
              filename = 'ueo.png'
          elif nz == '26':
              filename = 'zpp.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeCreator_2
Note: EIB_AUSSAGE
AttributeCreator_2
    ATTR_LIST = EIB_AUSSAGE_DE,@Value(BEZ),EIB_AUSSAGE_FR,@Value(BEZ)
    -> InlineQuerier [ZONE]
AlleAemter (input)
    -> AttributeKeeper
AttributeKeeper
    KEEP_ATTRS = AMT_XTF_ID,AMTNAME,UID_AMT,AMTIMWEB,AMT_ID
    -> InlineQuerier [AMT]
Note: AMT joinen
InlineQuerier
    QUERY_DEF:
      JOIN,SELECT a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,DATENVERW,text,ZUSTAENDIG,text,ZONE.fme_feature_content,fme_feature_content
    TABLE_DEF = AMT,AMT_XTF_ID,text,AMT_ID,text,ZONE,DATENVERW,text,ZUSTAENDIG,text
    JOIN -> AttributeKeeper_5
    JOIN -> AttributeKeeper_6
    JOIN -> AttributeKeeper_8
    JOIN -> AttributeKeeper_9
    JOIN -> AttributeKeeper_10
AttributeKeeper_8
    KEEP_ATTRS = DATENVERW,ZUSTAENDIG,GENEHM,INKRAFT,BESCHRIEB,PLANBESCHR,FLMASS,ZONENABK,BEZ,BR_NUTZART,BR_NMASS,NZ,GRUENFZ,BEMERK,DARST_C,RVS_ID,QUALITAET,VERBINDLKT,NZ_ART,LAERMES,KANTART,BUNDESART,NZ_TYP,BK_TYP
    -> GNZPPUEO (output)
GNZPPUEO (output)
AttributeKeeper_6
    KEEP_ATTRS = DAR_OID,EIB_SORT,STH_ID,EIB_XTF_ID,filecopy_dest_dataset,EIB_PUBLIZIERTAB,filecopy_source_dataset,RES_ID,EIB_OID,VERBINDLKT,EIB_ARTCODE,EIB_AUSSAGE_FR,EIB_LEGENDESYMBOL_DE,EIB_AUSSAGE_DE,EIB_LEGENDESYMBOL_FR
    -> AttributeFilter_2
Note: Nur Festlegungen kommen / in die Transferstruktur
AttributeFilter_2
    ATTR_NAME = VERBINDLKT
    ATTR_VALUES = <EMPTY>,<MISSING>,<NULL>,<UNFILTERED>,3
    3 -> AttributeRemover
AttributeRemover
    REMOVE_ATTRS = VERBINDLKT
    -> EIGENTUMSBESCHRAENKUNG (output)
EIGENTUMSBESCHRAENKUNG (output)
AttributeKeeper_9
    KEEP_ATTRS = RES_ID,FLA_OID,EIB_OID,FLA_PUBLIZIERTAB,VERBINDLKT
    -> AttributeFilter_3
Note: Nur Festlegungen kommen / in die Transferstruktur
AttributeFilter_3
    ATTR_NAME = VERBINDLKT
    ATTR_VALUES = <EMPTY>,<MISSING>,<NULL>,<UNFILTERED>,3
    3 -> AttributeRemover_2
AttributeRemover_2
    REMOVE_ATTRS = VERBINDLKT
    -> FLAECHE (output)
FLAECHE (output)
AttributeKeeper_10
    KEEP_ATTRS = EIB_XTF_ID,EIB_OID,VERBINDLKT
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> VerwendeteAemter (output)
VerwendeteAemter (output)
GN_ZonentypRV (input)
    -> AttributeKeeper_4
AttributeKeeper_4
    KEEP_ATTRS = rv_xtf_id,rv_Typ,rv_Vorschrift,rv_ArtikelNr
    -> AttributeKeeper_7
AttributeKeeper_7
    KEEP_ATTRS = rv_Typ,rv_Vorschrift,rv_ArtikelNr
    -> AttributeRenamer_3
AttributeRenamer_3
    ATTR_LIST = rv_ArtikelNr,HIV_ARTNR,"",rv_Vorschrift,Vorschrift,""
    -> FeatureMerger_2 [REQUESTOR]
FeatureMerger_2
    IGNORE_NULLS = Yes
    JOIN_KEYS = @Value(rv_Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeRemover_5
AttributeRemover_5
    REMOVE_ATTRS = rv_Typ,VERBINDLKT
    -> HINVOR (output)
HINVOR (output)

FME custom transformer Amt vorbereiten

Parameters:
- UID_AMT = @Value(UID_Amt)   # Uid Amt
- XTF_ID = @Value(xtf_id)   # Xtf Id
- AMTIMWEB = @Value(AmtImWeb)   # AmtImWeb
- NAME = @Value(Name)   # Name

Amt (input)
    -> UUIDGenerator_8
UUIDGenerator_8
    UUID_ATTR = AMT_ID
    -> AttributeRenamer_7
AttributeRenamer_7
    ATTR_LIST = Name,AMTNAME,"",AmtImWeb,AMTIMWEB,"",UID_Amt,UID_AMT,"",xtf_id,AMT_XTF_ID,""
    -> AMT (output)
AMT (output)

FME custom transformer UE_Abstandslinie

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- NUTZUNGSZIFFER_ART = @Value(Nutzungsziffer_Art)   # Nutzungsziffer Art
- DATENVERWALTUNGSSTELLE = @Value(Datenverwaltungsstelle)   # Datenverwaltungsstelle
- ZUSTAENDIGESTELLE = @Value(ZustaendigeStelle)   # ZustaendigeStelle
- GRUENFLAECHENZIFFER = @Value(Gruenflaechenziffer)   # Gruenflaechenziffer
- QUALITAET = @Value(Qualitaet)   # Qualitaet
- TYP = @Value(Typ)   # Typ
- NUTZUNGSZIFFER = @Value(Nutzungsziffer)   # Nutzungsziffer
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- VORSCHRIFT = @Value(Vorschrift)   # Vorschrift
- STATUS = @Value(Status)   # Status
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id

UE_LinienelementAbstand (input)
    -> AttributeKeeper
AttributeKeeper
    KEEP_ATTRS = Objekt,Beschrieb,Qualitaet,Inkraftsetzung,Genehmigung
    -> UUIDGenerator
Note: LIN_OID
UUIDGenerator
    UUID_ATTR = LIN_OID
    -> FeatureMerger [REQUESTOR]
UE_Abstandslinie (input)
    -> AttributeKeeper_4
AttributeKeeper_4
    KEEP_ATTRS = Bezeichnung,KantArt,xtf_id,Abkuerzung,Nutzungsziffer_Art,Datenverwaltungsstelle,ZustaendigeStelle,Gruenflaechenziffer,Nutzungsziffer,Bemerkung,DarstellungCode,Planbeschriftung,Verbindlichkeit,Status
    -> UUIDGenerator_2
Note: EIB_OID
UUIDGenerator_2
    UUID_ATTR = EIB_OID
    -> AttributeRenamer
AttributeRenamer
    ATTR_LIST = xtf_id,EIB_XTF_ID,"",KantArt,_kantart,""
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,LINIENABK,"",DarstellungCode,DARST_C,"",Nutzungsziffer,NZ,"",Gruenflaechenziffer,GRUENFZ,"",Datenverwaltungsstelle,DATENVERW,"",ZustaendigeStelle,ZUSTAENDIG,"",Status,STATUS,""
    -> AttributeCreator
AttributeCreator
    ATTR_LIST = RVS_ID,@Value(EIB_OID),EIB_AUSSAGE_DE,"FME_CONDITIONAL:DEFAULT_VALUE'@Value(BEZ)'BOOL_OP;OR;COMPOSITE_TEST;<Unused>;TEST @Value(PLANBESCHR) ATTRIBUTE_HAS_VALUE _FME_BLANK_STRING_'@Value(BEZ) (@Value(PLANBESCHR))'FME_NUM_CONDITIONS2___",EIB_AUSSAGE_FR,"FME_CONDITIONAL:DEFAULT_VALUE'@Value(BEZ)'BOOL_OP;OR;COMPOSITE_TEST;<Unused>;TEST @Value(PLANBESCHR) ATTRIBUTE_HAS_VALUE _FME_BLANK_STRING_'@Value(BEZ) (@Value(PLANBESCHR))'FME_NUM_CONDITIONS2___",EIB_ARTCODE,@Value(LINIENABK),EIB_SORT,@Evaluate(300+@int(@Value(_kantart))),RES_ID,1,STH_ID,14,LIN_PUBLIZIERTAB,@Value(EIB_PUBLIZIERTAB),DAR_OID,ch.be.bve.agi.npl.$(BFSNR).14
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          kantart = feature.getAttribute('_kantart')
          bez = feature.getAttribute('BEZ')
          status = feature.getAttribute('STATUS')

          filename = 'blspez.png'
          if kantart == '5' and bez == 'Baulinie':
              if status == '3':
                  filename = "blproj.png"
              else:
                  filename = 'bl.png'
          elif status == '3':
              filename = 'blspezproj.png'
          elif kantart == '4':
              filename = 'wbl.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeValueMapper
Note: KANTART mappen. / Interlis-Codelisten starten bei 0, / GeoDB-Wertetabellen bei 1!
AttributeValueMapper
    DIRECTION = Forward (Source To Destination)
    LUT = 0,23,1,24,2,25,3,26,4,28,5,29,6,30,7,31,8,32,9,33,10,34,11,35,12,36
    SRC = _kantart
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> AttributeKeeper_2
AttributeKeeper_2
    KEEP_ATTRS = AMT_XTF_ID,AMTNAME,UID_AMT,AMTIMWEB,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
    JOIN -> TestFilter
Note: Projektierte Baulinien / aussortieren
TestFilter
    DEFAULT_VALUE = ALLEANDEREN
    TEST_LIST = BOOL_OP,OR,COMPOSITE_TEST,<Unused>,TEST_CLAUSE,"TEST @Value(STATUS) = 3",PROJEKTIERT
    PROJEKTIERT -> AttributeCreator_2
    ALLEANDEREN -> AttributeRemover_3
Note: RES_ID wird absichtlich auf inKraft / gesetzt. Bis der Auszug mit laufenden / Änderungen umgehen kann!
AttributeCreator_2
    ATTR_LIST = RES_ID,1
    -> AttributeCreator_4
Note: String "(projektiert)" wird angehängt.
AttributeCreator_4
    ATTR_LIST = EIB_AUSSAGE_DE,@Value(EIB_AUSSAGE_DE) (projektiert),EIB_AUSSAGE_FR,@Value(EIB_AUSSAGE_FR) (projektiert)
    -> AttributeRemover_3
AttributeRemover_3
    REMOVE_ATTRS = xtf_id,Objekt,Qualitaet,Verbindlichkeit,KantArt,Nutzungsziffer_Art,_matched_records
    -> AttributeFilter_2
AttributeFilter_2
    ATTR_NAME = KANTART
    ATTR_VALUES = <EMPTY>,<MISSING>,<NULL>,<UNFILTERED>,28
    <UNFILTERED> -> AttributeRemover_4
    <UNFILTERED> -> AttributeRemover_8
    <UNFILTERED> -> AttributeKeeper_8
    <UNFILTERED> -> AttributeKeeper_6
    28 -> AttributeCreator_3
    28 -> AttributeRemover_8
AttributeKeeper_8
    KEEP_ATTRS = DAR_OID,GRUENFZ,STATUS,BEZ,BESCHRIEB,DARST_C,INKRAFT,VERBINDLKT,QUALITAET,DATENVERW,NZ_ART,BUNDESART,ZUSTAENDIG,GENEHM,PLANBESCHR,LINIENABK,NZ,RVS_ID,KANTART,BEMERK
    -> UELN (output)
UELN (output)
AttributeCreator_3
    ATTR_LIST = STH_ID,170,DAR_OID,ch.be.bve.agi.npl.$(BFSNR).170
    -> AttributeRemover_4
    -> AttributeKeeper_7
    -> AttributeKeeper_6
AttributeRemover_4
    REMOVE_ATTRS = GRUENFZ,STATUS,_kantart,BEZ,BESCHRIEB,DARST_C,INKRAFT,LIN_OID,QUALITAET,DATENVERW,LIN_PUBLIZIERTAB,NZ_ART,BUNDESART,ZUSTAENDIG,GENEHM,PLANBESCHR,LINIENABK,NZ,RVS_ID,KANTART,BEMERK
    -> AttributeFilter_4
Note: Nur Festlegungen kommen / in die Transferstruktur
AttributeFilter_4
    ATTR_NAME = VERBINDLKT
    ATTR_VALUES = <EMPTY>,<MISSING>,<NULL>,<UNFILTERED>,3
    3 -> AttributeRemover_2
AttributeRemover_2
    REMOVE_ATTRS = VERBINDLKT
    -> EIGENTUMSBESCHRAENKUNG (output)
EIGENTUMSBESCHRAENKUNG (output)
AttributeKeeper_6
    KEEP_ATTRS = LIN_PUBLIZIERTAB,RES_ID,EIB_OID,VERBINDLKT,LIN_OID
    -> AttributeFilter_3
Note: Nur Festlegungen kommen / in die Transferstruktur
AttributeFilter_3
    ATTR_NAME = VERBINDLKT
    ATTR_VALUES = <EMPTY>,<MISSING>,<NULL>,<UNFILTERED>,3
    3 -> AttributeRemover
AttributeRemover
    REMOVE_ATTRS = VERBINDLKT
    -> LINIE (output)
LINIE (output)
AttributeKeeper_7
    KEEP_ATTRS = GRUENFZ,BEZ,BESCHRIEB,DARST_C,INKRAFT,VERBINDLKT,QUALITAET,DATENVERW,NZ_ART,BUNDESART,ZUSTAENDIG,GENEHM,PLANBESCHR,LINIENABK,NZ,RVS_ID,KANTART,BEMERK
    -> UEWAABL (output)
UEWAABL (output)
AttributeRemover_8
    REMOVE_ATTRS = EIB_SORT,DAR_OID,GRUENFZ,EIB_AUSSAGE_DE,BEZ,BESCHRIEB,DARST_C,INKRAFT,LIN_OID,QUALITAET,STH_ID,DATENVERW,LIN_PUBLIZIERTAB,NZ_ART,BUNDESART,EIB_PUBLIZIERTAB,ZUSTAENDIG,GENEHM,PLANBESCHR,LINIENABK,NZ,RVS_ID,EIB_AUSSAGE_FR,RES_ID,KANTART,BEMERK,EIB_ARTCODE
    -> FeatureMerger_2 [SUPPLIER]
AttributeRemover_6
    REMOVE_ATTRS = xtf_id,Objekt,BESCHRIEB,Qualitaet,INKRAFT,GENEHM,Vorschrift,LIN_OID,BEZ,KantArt,EIB_XTF_ID,LINIENABK,Nutzungsziffer_Art,GRUENFZ,NZ,BEMERK,DARST_C,PLANBESCHR,Verbindlichkeit,EIB_OID,EIB_PUBLIZIERTAB,RVS_ID,EIB_AUSSAGE_DE,EIB_AUSSAGE_FR,EIB_ARTCODE,EIB_SORT,RES_ID,STH_ID,LIN_PUBLIZIERTAB,DAR_OID,QUALITAET,VERBINDLKT,NZ_ART,KANTART,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
UE_AbstandslinieRV (input)
    -> AttributeKeeper_3
AttributeKeeper_3
    KEEP_ATTRS = Typ,ArtikelNr,Vorschrift
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_5
AttributeKeeper_5
    KEEP_ATTRS = HIV_ARTNR,Vorschrift,EIB_XTF_ID,EIB_OID
    -> HINVOR (output)
HINVOR (output)

FME custom transformer GR_Gewaesserraum

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- OBJEKT = @Value(Objekt)   # Objekt
- TYP = @Value(Typ)   # Typ
- ABSTANDRECHTS = @Value(AbstandRechts)   # AbstandRechts
- ZUSTAENDIGESTELLE = @Value(ZustaendigeStelle)   # ZustaendigeStelle
- ABSTANDLINKS = @Value(AbstandLinks)   # AbstandLinks
- ABSTANDDEFINITION = @Value(AbstandDefinition)   # AbstandDefinition
- GENEHMIGUNG = @Value(Genehmigung)   # Genehmigung
- BEMERKUNG = @Value(Bemerkung)   # Bemerkung
- BEZEICHNUNG = @Value(Bezeichnung)   # Bezeichnung
- VORSCHRIFT = @Value(Vorschrift)   # Vorschrift

GR_Gewaesserraumflaeche (input)
    -> UUIDGenerator
Note: FLA_OID
UUIDGenerator
    UUID_ATTR = FLA_OID
    -> AttributeCreator_3
AttributeCreator_3
    ATTR_LIST = KANTART,18
    -> AttributeRemover
GR_Gewaesserraumlinie (input)
    -> UUIDGenerator_2
Note: LIN_OID
UUIDGenerator_2
    UUID_ATTR = LIN_OID
    -> AttributeCreator_4
AttributeCreator_4
    ATTR_LIST = KANTART,27
    -> AttributeRemover
AttributeRemover
    REMOVE_ATTRS = Verbindlichkeit,xtf_id,ArtikelNr,Datenverwaltungsstelle,DarstellungCode,Typ,ZustaendigeStelle,Bemerkung,Bezeichnung
    -> FeatureMerger [REQUESTOR]
GR_Gewaesserraum (input)
    -> UUIDGenerator_4
Note: EIB_OID
UUIDGenerator_4
    UUID_ATTR = EIB_OID
    -> AttributeRenamer
AttributeRenamer
    ATTR_LIST = xtf_id,EIB_XTF_ID,""
    -> AttributeRemover_2
AttributeRemover_2
    REMOVE_ATTRS = ArtikelNr,Inkraftsetzung,Qualitaet,Objekt,Typ,AbstandRechts,AbstandLinks,AbstandDefinition,Genehmigung
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",DarstellungCode,DARST_C,"",Datenverwaltungsstelle,DATENVERW,"",ZustaendigeStelle,ZUSTAENDIG,"",Bemerkung,BEMERK,"",AbstandLinks,ABSTLINKS,"",AbstandRechts,ABSTRECHTS,""
    -> AttributeCreator
AttributeCreator
    ATTR_LIST = RVS_ID,@Value(EIB_OID),EIB_AUSSAGE_DE,@Value(BEZ),EIB_AUSSAGE_FR,@Value(BEZ),EIB_SORT,700,RES_ID,1,FLA_PUBLIZIERTAB,@Value(EIB_PUBLIZIERTAB),LIN_PUBLIZIERTAB,@Value(EIB_PUBLIZIERTAB),EIB_ARTCODE,""
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: ABSTDEF mappen. / Interlis-Codelisten starten bei 0, / GeoDB-Wertetabellen bei 1!
AttributeValueMapper_4
    DIRECTION = Forward (Source To Destination)
    LUT = 0,1,1,2,2,3
    SRC = AbstandDefinition
    VAL_ATTR = ABSTDEF
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
    JOINED -> AttributeRemover_3
AttributeRemover_3
    REMOVE_ATTRS = Qualitaet,Objekt,Vorschrift,Verbindlichkeit,_matched_records
    -> FeatureTypeFilter
FeatureTypeFilter
    ATTRIBUTES = <BLANK>,<UNFILTERED>,DM16NplBE_Bern.Nutzungsplanung.GR_Gewaesserraumflaeche,DM16NplBE_Bern.Nutzungsplanung.GR_Gewaesserraumlinie
    DM16NplBE_Bern.Nutzungsplanung.GR_Gewaesserraumflaeche -> PythonCaller
    DM16NplBE_Bern.Nutzungsplanung.GR_Gewaesserraumflaeche -> AttributeRemover_8
    DM16NplBE_Bern.Nutzungsplanung.GR_Gewaesserraumlinie -> PythonCaller_2
    DM16NplBE_Bern.Nutzungsplanung.GR_Gewaesserraumlinie -> AttributeRemover_8
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          filename = 'gewraum_fl.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeCreator_5
AttributeCreator_5
    ATTR_LIST = STH_ID,12,DAR_OID,ch.be.bve.agi.npl.$(BFSNR).12
    -> AttributeRemover_4
    -> UEFL (output)
    -> AttributeFilter_3
UEFL (output)
Note: Nur Festlegungen kommen / in die Transferstruktur
AttributeFilter_3
    ATTR_NAME = VERBINDLKT
    ATTR_VALUES = <EMPTY>,<MISSING>,<NULL>,<UNFILTERED>,3
    3 -> AttributeKeeper
AttributeKeeper
    KEEP_ATTRS = RES_ID,FLA_OID,EIB_OID,FLA_PUBLIZIERTAB
    -> FLAECHE (output)
FLAECHE (output)
Note: Legendenbilder
PythonCaller_2
    NEW_ATTRIBUTES = EIB_LEGENDESYMBOL_DE EIB_LEGENDESYMBOL_FR filecopy_source_dataset filecopy_dest_dataset
    PYTHONSOURCE:
      import fmeobjects
      import os

      def processFeature(feature):

          filename = 'gewraum_l.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeCreator_6
AttributeCreator_6
    ATTR_LIST = STH_ID,14,DAR_OID,ch.be.bve.agi.npl.$(BFSNR).14
    -> AttributeRemover_4
    -> UELN (output)
    -> AttributeFilter_5
AttributeRemover_4
    REMOVE_ATTRS = FLA_OID,BEZ,DARST_C,INKRAFT,LIN_OID,QUALITAET,ABSTDEF,DATENVERW,ABSTLINKS,LIN_PUBLIZIERTAB,BUNDESART,ZUSTAENDIG,AbstandDefinition,GENEHM,FLA_PUBLIZIERTAB,RVS_ID,ABSTRECHTS,KANTART,BEMERK
    -> AttributeFilter_2
AttributeFilter_2
    ATTR_NAME = VERBINDLKT
    ATTR_VALUES = <EMPTY>,<MISSING>,<NULL>,<UNFILTERED>,3
    3 -> AttributeRemover_7
AttributeRemover_7
    REMOVE_ATTRS = VERBINDLKT
    -> EIGENTUMSBESCHRAENKUNG (output)
EIGENTUMSBESCHRAENKUNG (output)
UELN (output)
Note: Nur Festlegungen kommen / in die Transferstruktur
AttributeFilter_5
    ATTR_NAME = VERBINDLKT
    ATTR_VALUES = <EMPTY>,<MISSING>,<NULL>,<UNFILTERED>,3
    3 -> AttributeKeeper_2
AttributeKeeper_2
    KEEP_ATTRS = LIN_PUBLIZIERTAB,RES_ID,EIB_OID,LIN_OID
    -> LINIE (output)
LINIE (output)
AttributeRemover_8
    REMOVE_ATTRS = EIB_SORT,FLA_OID,EIB_AUSSAGE_DE,BEZ,DARST_C,INKRAFT,LIN_OID,QUALITAET,ABSTDEF,DATENVERW,ABSTLINKS,LIN_PUBLIZIERTAB,BUNDESART,EIB_PUBLIZIERTAB,ZUSTAENDIG,AbstandDefinition,GENEHM,FLA_PUBLIZIERTAB,RVS_ID,EIB_AUSSAGE_FR,RES_ID,ABSTRECHTS,KANTART,BEMERK,EIB_ARTCODE
    -> FeatureMerger_2 [SUPPLIER]
Alle_Aemter (input)
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
AttributeRemover_6
    REMOVE_ATTRS = xtf_id,INKRAFT,Qualitaet,Objekt,ABSTRECHTS,ABSTLINKS,AbstandDefinition,GENEHM,Vorschrift,FLA_OID,KANTART,LIN_OID,Verbindlichkeit,EIB_XTF_ID,DARST_C,BEMERK,BEZ,EIB_OID,EIB_PUBLIZIERTAB,RVS_ID,EIB_AUSSAGE_DE,EIB_AUSSAGE_FR,EIB_SORT,RES_ID,FLA_PUBLIZIERTAB,LIN_PUBLIZIERTAB,EIB_ARTCODE,QUALITAET,VERBINDLKT,ABSTDEF,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
GR_GewaesserraumRV (input)
    -> AttributeRemover_5
AttributeRemover_5
    REMOVE_ATTRS = Verbindlichkeit,xtf_id,Inkraftsetzung,Datenverwaltungsstelle,DarstellungCode,Qualitaet,Objekt,AbstandRechts,ZustaendigeStelle,AbstandLinks,AbstandDefinition,Genehmigung,Bemerkung,Bezeichnung
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeRemover_9
AttributeRemover_9
    REMOVE_ATTRS = Typ,VERBINDLKT
    -> HINVOR (output)
HINVOR (output)

FME custom transformer Dokument vorbereiten

Parameters:
- OFFIZIELLERTITEL = @Value(OffiziellerTitel)   # OffiziellerTitel
- TITEL = @Value(Titel)   # Titel
- XTF_ID = @Value(xtf_id)   # Xtf Id
- DOKUMENT = @Value(Dokument)   # Dokument
- ABKUERZUNG = @Value(Abkuerzung)   # Abkuerzung
- GEMEINDE = @Value(Gemeinde)   # Gemeinde
- ART_DOKU = @Value(Art_Doku)   # Art Doku
- ZUSTAENDIGESTELLE = @Value(ZustaendigeStelle)   # ZustaendigeStelle
- OFFIZIELLENR = @Value(OffizielleNr)   # OffizielleNr
- AMT_XTF_ID = @Value(AMT_XTF_ID)   # Amt Xtf Id
- AMT_ID = @Value(AMT_ID)   # Amt Id

Dokument (input)
    -> AttributeRemover_2
AttributeRemover_2
    REMOVE_ATTRS = AMT_XTF_ID,AMT_ID
    -> UUIDGenerator_5
Note: VOR_OID
UUIDGenerator_5
    UUID_ATTR = VOR_OID
    -> TimeStamper_2
TimeStamper_2
    FMT = FME Date (^Y^m^d)
    TIME_ATTR = VOR_PUBLIZIERTAB
    -> AttributeValueMapper
AttributeValueMapper
    DIRECTION = Forward (Source To Destination)
    LUT = 0,1,1,3
    SRC = Art_Doku
    VAL_ATTR = VOA_ID
    -> AttributeRenamer_4
AttributeRenamer_4
    ATTR_LIST = xtf_id,VOR_XTF_ID,"",Titel,VOR_TITEL_DE,"",OffiziellerTitel,VOR_OFFIZIELLERTITEL_DE,"",Abkuerzung,VOR_ABKUERZUNG_DE,"",OffizielleNr,VOR_OFFIZIELLENR,""
    -> AttributeCreator_4
AttributeCreator_4
    ATTR_LIST = VOR_TITEL_FR,@Value(VOR_TITEL_DE),VOR_OFFIZIELLERTITEL_FR,@Value(VOR_OFFIZIELLERTITEL_DE),VOR_ABKUERZUNG_FR,@Value(VOR_ABKUERZUNG_DE),ZustaendigeStelle,@Value(ZustaendigeStelle),Dokument,@Value(Dokument),Gemeinde,@Value(Gemeinde)
    -> PythonCaller
PythonCaller
    NEW_ATTRIBUTES = VOR_TEXTIMWEB_DE VOR_TEXTIMWEB_FR filecopy_source_dataset filecopy_dest_dataset
    PYTHONSOURCE:
      import fmeobjects
      import os

      def processFeature(feature):
          filename = feature.getAttribute('Dokument')

          outputURL = FME_MacroValues['OUTPUT_RV_URL'] + filename

          inputFile = os.path.join(FME_MacroValues['INPUT_RV_DIR'], filename)
          inputFile = inputFile.replace('\\','/')

          outputDir = FME_MacroValues['OUTPUT_RV_DIR'].replace('\\','/')

          feature.setAttribute('VOR_TEXTIMWEB_DE', outputURL)
          feature.setAttribute('VOR_TEXTIMWEB_FR', outputURL)
          feature.setAttribute('filecopy_source_dataset', inputFile)
          feature.setAttribute('filecopy_dest_dataset', outputDir)
    PYTHONSYMBOL = processFeature
    -> FeatureMerger [REQUESTOR]
Amt (input)
    -> AttributeRemover
AttributeRemover
    REMOVE_ATTRS = OffiziellerTitel,ZustaendigeStelle,Titel,Abkuerzung,OffizielleNr,Gemeinde,xtf_id,Dokument,Art_Doku
    -> AttributeRenamer
AttributeRenamer
    ATTR_LIST = AMT_ID,ZUSTAENDIG,""
    -> FeatureMerger [SUPPLIER]
FeatureMerger
    IGNORE_NULLS = Yes
    JOIN_KEYS = @Value(ZustaendigeStelle) @Value(AMT_XTF_ID) AUTO
    MERGE_TYPE = Attributes Only
    PROCESS_DUPS = No
    SUPPLIERS_FIRST = No
    SUPPLIER_PREFIX_DUMMY = YES
    MERGED -> Alle_Dokumente (output)
Alle_Dokumente (output)

FME custom transformer GN_Bauklassen

Parameters:
- GEODB_DATABASE =   # GeoDB-Database
- GEODB_USERNAME =   # GeoDB-Username
- GEODB_PASSWORD =   # GeoDB-Passwort
- BFSNR =   # BFS-Nummer
- RV_XTF_ID = @Value(rv_xtf_id)   # Rv Xtf Id
- RV_TYP = @Value(rv_Typ)   # Rv Typ
- RV_VORSCHRIFT = @Value(rv_Vorschrift)   # Rv Vorschrift
- RV_ARTIKELNR = @Value(rv_ArtikelNr)   # Rv Artikelnr
- ZT_XTF_ID = @Value(zt_xtf_id)   # Zt Xtf Id
- ZT_VERBINDLICHKEIT = @Value(zt_Verbindlichkeit)   # Zt Verbindlichkeit
- ZT_KANTART = @Value(zt_KantArt)   # Zt Kantart
- ZT_ABKUERZUNG = @Value(zt_Abkuerzung)   # Zt Abkuerzung
- ZT_BEZEICHNUNG = @Value(zt_Bezeichnung)   # Zt Bezeichnung
- ZT_BR_NUTZUNGSART = @Value(zt_BR_Nutzungsart)   # Zt Br Nutzungsart
- ZT_BR_NUTZUNGSMASS = @Value(zt_BR_Nutzungsmass)   # Zt Br Nutzungsmass
- ZT_NUTZUNGSZIFFER = @Value(zt_Nutzungsziffer)   # Zt Nutzungsziffer
- ZT_NUTZUNGSZIFFER_ART = @Value(zt_Nutzungsziffer_Art)   # Zt Nutzungsziffer Art
- ZT_GRUENFLAECHENZIFFER = @Value(zt_Gruenflaechenziffer)   # Zt Gruenflaechenziffer
- ZT_BEMERKUNG = @Value(zt_Bemerkung)   # Zt Bemerkung
- ZT_DATENVERWALTUNGSSTELLE = @Value(zt_Datenverwaltungsstelle)   # Zt Datenverwaltungsstelle
- ZT_ZUSTAENDIGESTELLE = @Value(zt_ZustaendigeStelle)   # Zt Zustaendigestelle
- ZT_NUTZUNGSZONE = @Value(zt_Nutzungszone)   # Zt Nutzungszone
- ZT_DARSTELLUNGCODENZ = @Value(zt_DarstellungCodeNZ)   # Zt Darstellungcodenz
- ZT_BAUKLASSE = @Value(zt_Bauklasse)   # Zt Bauklasse
- ZT_DARSTELLUNGCODEBK = @Value(zt_DarstellungCodeBK)   # Zt Darstellungcodebk
- GZ_XTF_ID = @Value(gz_xtf_id)   # Gz Xtf Id
- GZ_ZONENTYPREF = @Value(gz_ZonentypRef)   # Gz Zonentypref
- GZ_GENEHMIGUNG = @Value(gz_Genehmigung)   # Gz Genehmigung
- GZ_INKRAFTSETZUNG = @Value(gz_Inkraftsetzung)   # Gz Inkraftsetzung
- GZ_LAERMEMPFINDLICHKEIT = @Value(gz_Laermempfindlichkeit)   # Gz Laermempfindlichkeit
- GZ_BESCHRIEB = @Value(gz_Beschrieb)   # Gz Beschrieb
- GZ_PLANBESCHRIFTUNG = @Value(gz_Planbeschriftung)   # Gz Planbeschriftung
- GZ_QUALITAET = @Value(gz_Qualitaet)   # Gz Qualitaet
- GZ_BEMERKUNG = @Value(gz_Bemerkung)   # Gz Bemerkung
- GZ_FLAECHENMASS = @Value(gz_Flaechenmass)   # Gz Flaechenmass
- LEGEND_BASEURL =
- LEGEND_BASEDIR =
- LEGEND_INPUTDIR =

GN_Grundzone (input)
    -> AttributeKeeper_2
AttributeKeeper_2
    KEEP_ATTRS = gz_xtf_id,gz_ZonentypRef,gz_Genehmigung,gz_Inkraftsetzung,gz_Laermempfindlichkeit,gz_Beschrieb,gz_Planbeschriftung,gz_Qualitaet,gz_Bemerkung,gz_Flaechenmass
    -> UUIDGenerator_2
Note: FLA_OID
UUIDGenerator_2
    UUID_ATTR = FLA_OID
    -> AttributeRenamer_5
AttributeRenamer_5
    ATTR_LIST = gz_xtf_id,FLA_XTF_ID,""
    -> FeatureMerger [REQUESTOR]
GN_Zonentyp (input)
    -> AttributeKeeper_3
AttributeKeeper_3
    KEEP_ATTRS = zt_xtf_id,zt_Verbindlichkeit,zt_KantArt,zt_Abkuerzung,zt_Bezeichnung,zt_BR_Nutzungsart,zt_BR_Nutzungsmass,zt_Nutzungsziffer,zt_Nutzungsziffer_Art,zt_Gruenflaechenziffer,zt_Bemerkung,zt_Datenverwaltungsstelle,zt_ZustaendigeStelle,zt_Nutzungszone,zt_DarstellungCodeNZ,zt_Bauklasse,zt_DarstellungCodeBK
    -> UUIDGenerator
Note: EIB_OID
UUIDGenerator
    UUID_ATTR = EIB_OID
    -> AttributeRenamer
AttributeRenamer
    ATTR_LIST = zt_xtf_id,EIB_XTF_ID,""
    -> AttributeFilter
Note: Nach Festlegung / Gemeinde filtern
AttributeFilter
    ATTR_NAME = zt_Verbindlichkeit
    ATTR_VALUES = <EMPTY>,<MISSING>,<NULL>,<UNFILTERED>,2
    2 -> FeatureMerger [SUPPLIER]
FeatureMerger
    IGNORE_NULLS = Yes
    JOIN_KEYS = @Value(gz_ZonentypRef) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = gz_Genehmigung,GENEHM,"",gz_Inkraftsetzung,INKRAFT,"",gz_Beschrieb,BESCHRIEB,"",zt_Bezeichnung,BEZ,"",gz_Planbeschriftung,PLANBESCHR,"",zt_Bemerkung,BEMERK,"",zt_Abkuerzung,ZONENABK,"",zt_DarstellungCodeBK,DARST_C_BK,"",zt_BR_Nutzungsart,BR_NUTZART,"",zt_BR_Nutzungsmass,BR_NMASS,"",zt_Nutzungsziffer,NZ,"",zt_Gruenflaechenziffer,GRUENFZ,"",gz_Flaechenmass,FLMASS,"",zt_Datenverwaltungsstelle,DATENVERW,"",zt_ZustaendigeStelle,ZUSTAENDIG,"",zt_DarstellungCodeNZ,DARST_C_NZ,""
    -> AttributeCreator
AttributeCreator
    ATTR_LIST = RVS_ID,@Value(EIB_OID),EIB_ARTCODE,@Value(ZONENABK),EIB_SORT,@Evaluate(130+@int(@Value(zt_Bauklasse))),RES_ID,1,STH_ID,17,FLA_PUBLIZIERTAB,@Value(EIB_PUBLIZIERTAB),DAR_OID,ch.be.bve.agi.npl.$(BFSNR).17
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = gz_Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3
    SRC = zt_Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = zt_Nutzungsziffer_Art
    VAL_ATTR = NZ_ART
    -> AttributeValueMapper
Note: LAERMES mappen. / Inerlis-Codeliste startet bei 0, / die GeoDB-Wertetabelle hier / bei 7 (UEARTKTT)
AttributeValueMapper
    DIRECTION = Forward (Source To Destination)
    LUT = 0,7,1,8,2,9,3,10,4,11,5,12
    SRC = gz_Laermempfindlichkeit
    VAL_ATTR = LAERMES
    -> AttributeValueMapper_5
Note: KANTART mappen. / Interlis-Codelisten starten bei 0, / GeoDB-Wertetabellen bei 1! / Achtung: Bern hat zwei zusätliche / Werte!!!
AttributeValueMapper_5
    DIRECTION = Forward (Source To Destination)
    LUT = 0,W1,1,W2,2,W3,3,W4,4,W5,5,W6plus,6,WE,7,FH,8,M2,9,M3,10,M4,11,M5,12,M6plus,13,ME,14,KS,15,KL,16,HT,17,WEZ,18,B_E,19,BH,20,A,21,ZOEN,22,SKI,23,ZSF,24,GR,25,GB,26,LWZ,27,ILW,28,AA,29,ZMN,30,UEO,31,ZPP,32,SBV,33,USP,34,Uebrige
    SRC = zt_KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Zero or One (1:0..1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_NPZONET
    JOINED -> AttributeValueMapper_23
Note: NZ_TYP mappen.
AttributeValueMapper_23
    DIRECTION = Forward (Source To Destination)
    LUT = 0,unbekannt,1,Wohnzone (W),10,Freifläche A* (Zone für priv. Bauten + Anl. im allg. Int. FA*),11,Freifläche B* (Zone für priv. Bauten + Anl. im allg. Int. FB*),12,Freifläche C* (Zone für priv. Bauten + Anl. im allg. Int. FC*),13,Freifläche D* (Zone für priv. Bauten + Anl. im allg. Int. FD*),14,Schutzzone A (SZA) Landschafts- + Ortsbildschutzareal,15,Schutzzone B (SZB) Landschafts- + Ortsbildschutzareal,16,Schutzzone C (SZC) Naturschutzareal,17,Obere Altstadt, Zone mit Planungspflicht,18,Untere Altstadt und Wohngebiet Matte,19,Gewerbegebiete Matte, Zone mit Planungspflicht,2,Gemischte Wohnzone (WG),20,Landwirtschaftszone,21,Weilerzone,22,Übriges Gebiet: Wald,23,Übriges Gebiet: Gewässer,24,Übriges Gebiet: Verkehrsfläche ausserhalb Siedlungsgebiet,25,Überbauungsordnung,26,Zone mit Planungspflicht,27,Übriges Gebiet: andere,3,Kernzone (K),4,Dienstleistungszone (D),5,Industrie- und Gewerbezone (IG),6,Freifläche A (Zone für öff. Nutzungen FA),7,Freifläche B (Zone für öff. Nutzungen FB),8,Freifläche C (Zone für öff. Nutzungen FC),9,Freifläche D (Zone für öff. Nutzungen FD)
    SRC = zt_Nutzungszone
    VAL_ATTR = NZ_TYP
    -> AttributeValueMapper_22
Note: BK_TYP mappen
AttributeValueMapper_22
    DIRECTION = Forward (Source To Destination)
    LUT = 0,unbekannt,1,Bauklasse 1,10,Obere Altstadt, Zone mit Planungspflicht,11,Untere Altstadt und Wohngebiet Matte,12,Gewerbegebiete Matte, Zone mit Planungspflicht,13,Landwirtschaftszone,14,Weilerzone,15,Übriges Gebiet: Wald,16,Übriges Gebiet: Gewässer,17,Übriges Gebiet: Verkehrsfläche ausserhalb Siedlungsgebiet,18,Überbauungsordnung,19,Zone mit Planungspflicht,20,Übriges Gebiet: andere,2,Bauklasse 2,3,Bauklasse 3,4,Bauklasse 4,5,Bauklasse 5,6,Bauklasse 6,7,Bauklasse E, Erhaltung der best. Bebauungsstruktur,8,Festlegung der Bebauung mittels spezieller Vorschriften,9,Zone im öffentlichen Interesse
    SRC = zt_Bauklasse
    VAL_ATTR = BK_TYP
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          bk = feature.getAttribute('zt_Bauklasse')
          filename = 'bk' + unicode(bk) + '.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeCreator_2
Note: EIB_AUSSAGE
AttributeCreator_2
    ATTR_LIST = EIB_AUSSAGE_DE,@Value(BK_TYP),EIB_AUSSAGE_FR,@Value(BK_TYP)
    -> AttributeKeeper_10
    -> AttributeKeeper_9
    -> AttributeKeeper_6
AttributeKeeper_6
    KEEP_ATTRS = EIB_XTF_ID,EIB_OID,EIB_PUBLIZIERTAB,EIB_ARTCODE,EIB_SORT,RES_ID,STH_ID,DAR_OID,EIB_LEGENDESYMBOL_DE,EIB_LEGENDESYMBOL_FR,filecopy_source_dataset,filecopy_dest_dataset,EIB_AUSSAGE_DE,EIB_AUSSAGE_FR
    -> EIGENTUMSBESCHRAENKUNG (output)
EIGENTUMSBESCHRAENKUNG (output)
AttributeKeeper_9
    KEEP_ATTRS = FLA_OID,EIB_OID,RES_ID,FLA_PUBLIZIERTAB
    -> FLAECHE (output)
FLAECHE (output)
AttributeKeeper_10
    KEEP_ATTRS = EIB_XTF_ID,EIB_OID
    -> FeatureMerger_2 [SUPPLIER]
GN_ZonentypRV (input)
    -> AttributeKeeper_4
AttributeKeeper_4
    KEEP_ATTRS = rv_xtf_id,rv_Typ,rv_Vorschrift,rv_ArtikelNr
    -> AttributeKeeper_7
AttributeKeeper_7
    KEEP_ATTRS = rv_Typ,rv_Vorschrift,rv_ArtikelNr
    -> AttributeRenamer_3
AttributeRenamer_3
    ATTR_LIST = rv_ArtikelNr,HIV_ARTNR,"",rv_Vorschrift,Vorschrift,""
    -> FeatureMerger_2 [REQUESTOR]
FeatureMerger_2
    IGNORE_NULLS = Yes
    JOIN_KEYS = @Value(rv_Typ) @Value(EIB_XTF_ID) AUTO
    MERGE_TYPE = Attributes Only
    PROCESS_DUPS = No
    SUPPLIERS_FIRST = No
    SUPPLIER_PREFIX_DUMMY = YES
    MERGED -> AttributeRemover_5
AttributeRemover_5
    REMOVE_ATTRS = rv_Typ
    -> HINVOR (output)
HINVOR (output)

FME custom transformer GN_Nutzungszonen

Parameters:
- GZ_XTF_ID = @Value(gz_xtf_id)   # Gz Xtf Id
- GZ_ZONENTYPREF = @Value(gz_ZonentypRef)   # Gz Zonentypref
- GZ_GENEHMIGUNG = @Value(gz_Genehmigung)   # Gz Genehmigung
- GZ_INKRAFTSETZUNG = @Value(gz_Inkraftsetzung)   # Gz Inkraftsetzung
- GZ_LAERMEMPFINDLICHKEIT = @Value(gz_Laermempfindlichkeit)   # Gz Laermempfindlichkeit
- GZ_BESCHRIEB = @Value(gz_Beschrieb)   # Gz Beschrieb
- GZ_PLANBESCHRIFTUNG = @Value(gz_Planbeschriftung)   # Gz Planbeschriftung
- GZ_QUALITAET = @Value(gz_Qualitaet)   # Gz Qualitaet
- GZ_BEMERKUNG = @Value(gz_Bemerkung)   # Gz Bemerkung
- GZ_FLAECHENMASS = @Value(gz_Flaechenmass)   # Gz Flaechenmass
- RV_XTF_ID = @Value(rv_xtf_id)   # Rv Xtf Id
- RV_TYP = @Value(rv_Typ)   # Rv Typ
- RV_VORSCHRIFT = @Value(rv_Vorschrift)   # Rv Vorschrift
- RV_ARTIKELNR = @Value(rv_ArtikelNr)   # Rv Artikelnr
- ZT_XTF_ID = @Value(zt_xtf_id)   # Zt Xtf Id
- ZT_VERBINDLICHKEIT = @Value(zt_Verbindlichkeit)   # Zt Verbindlichkeit
- ZT_KANTART = @Value(zt_KantArt)   # Zt Kantart
- ZT_ABKUERZUNG = @Value(zt_Abkuerzung)   # Zt Abkuerzung
- ZT_BEZEICHNUNG = @Value(zt_Bezeichnung)   # Zt Bezeichnung
- ZT_BR_NUTZUNGSART = @Value(zt_BR_Nutzungsart)   # Zt Br Nutzungsart
- ZT_BR_NUTZUNGSMASS = @Value(zt_BR_Nutzungsmass)   # Zt Br Nutzungsmass
- ZT_NUTZUNGSZIFFER = @Value(zt_Nutzungsziffer)   # Zt Nutzungsziffer
- ZT_NUTZUNGSZIFFER_ART = @Value(zt_Nutzungsziffer_Art)   # Zt Nutzungsziffer Art
- ZT_GRUENFLAECHENZIFFER = @Value(zt_Gruenflaechenziffer)   # Zt Gruenflaechenziffer
- ZT_BEMERKUNG = @Value(zt_Bemerkung)   # Zt Bemerkung
- ZT_DATENVERWALTUNGSSTELLE = @Value(zt_Datenverwaltungsstelle)   # Zt Datenverwaltungsstelle
- ZT_ZUSTAENDIGESTELLE = @Value(zt_ZustaendigeStelle)   # Zt Zustaendigestelle
- ZT_NUTZUNGSZONE = @Value(zt_Nutzungszone)   # Zt Nutzungszone
- ZT_DARSTELLUNGCODENZ = @Value(zt_DarstellungCodeNZ)   # Zt Darstellungcodenz
- ZT_BAUKLASSE = @Value(zt_Bauklasse)   # Zt Bauklasse
- ZT_DARSTELLUNGCODEBK = @Value(zt_DarstellungCodeBK)   # Zt Darstellungcodebk
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- GEODB_DATABASE =   # GeoDB-Database
- GEODB_USERNAME =   # GeoDB-Username
- GEODB_PASSWORD =   # GeoDB-Passwort
- BFSNR =   # BFS-Nummer

GN_Zonentyp (input)
    -> AttributeKeeper_3
AttributeKeeper_3
    KEEP_ATTRS = zt_xtf_id,zt_Verbindlichkeit,zt_KantArt,zt_Abkuerzung,zt_Bezeichnung,zt_BR_Nutzungsart,zt_BR_Nutzungsmass,zt_Nutzungsziffer,zt_Nutzungsziffer_Art,zt_Gruenflaechenziffer,zt_Bemerkung,zt_Datenverwaltungsstelle,zt_ZustaendigeStelle,zt_Nutzungszone,zt_DarstellungCodeNZ,zt_Bauklasse,zt_DarstellungCodeBK
    -> UUIDGenerator
Note: EIB_OID
UUIDGenerator
    UUID_ATTR = EIB_OID
    -> AttributeRenamer
AttributeRenamer
    ATTR_LIST = zt_xtf_id,EIB_XTF_ID,""
    -> AttributeFilter
Note: Nach Festlegung Gemeinde / und Hinweise filtern
AttributeFilter
    ATTR_NAME = zt_Verbindlichkeit
    ATTR_VALUES = <EMPTY>,<MISSING>,<NULL>,<UNFILTERED>,2,3
    2 -> FeatureMerger [SUPPLIER]
    3 -> FeatureMerger [SUPPLIER]
GN_Grundzone (input)
    -> AttributeKeeper_2
AttributeKeeper_2
    KEEP_ATTRS = gz_xtf_id,gz_ZonentypRef,gz_Genehmigung,gz_Inkraftsetzung,gz_Laermempfindlichkeit,gz_Beschrieb,gz_Planbeschriftung,gz_Qualitaet,gz_Bemerkung,gz_Flaechenmass
    -> UUIDGenerator_2
Note: FLA_OID
UUIDGenerator_2
    UUID_ATTR = FLA_OID
    -> AttributeRenamer_5
AttributeRenamer_5
    ATTR_LIST = gz_xtf_id,FLA_XTF_ID,""
    -> FeatureMerger [REQUESTOR]
FeatureMerger
    IGNORE_NULLS = Yes
    JOIN_KEYS = @Value(gz_ZonentypRef) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = gz_Genehmigung,GENEHM,"",gz_Inkraftsetzung,INKRAFT,"",gz_Beschrieb,BESCHRIEB,"",zt_Bezeichnung,BEZ,"",gz_Planbeschriftung,PLANBESCHR,"",zt_Bemerkung,BEMERK,"",zt_Abkuerzung,ZONENABK,"",zt_DarstellungCodeBK,DARST_C_BK,"",zt_BR_Nutzungsart,BR_NUTZART,"",zt_BR_Nutzungsmass,BR_NMASS,"",zt_Nutzungsziffer,NZ,"",zt_Gruenflaechenziffer,GRUENFZ,"",gz_Flaechenmass,FLMASS,"",zt_Datenverwaltungsstelle,DATENVERW,"",zt_ZustaendigeStelle,ZUSTAENDIG,"",zt_DarstellungCodeNZ,DARST_C_NZ,""
    -> AttributeCreator
AttributeCreator
    ATTR_LIST = RVS_ID,@Value(EIB_OID),EIB_ARTCODE,@Value(ZONENABK),EIB_SORT,@Evaluate(100+@int(@Value(zt_Nutzungszone))),RES_ID,1,STH_ID,16,FLA_PUBLIZIERTAB,@Value(EIB_PUBLIZIERTAB),DAR_OID,ch.be.bve.agi.npl.$(BFSNR).16
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = gz_Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = zt_Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = zt_Nutzungsziffer_Art
    VAL_ATTR = NZ_ART
    -> AttributeValueMapper
Note: LAERMES mappen. / Inerlis-Codeliste startet bei 0, / die GeoDB-Wertetabelle hier / bei 7 (UEARTKTT)
AttributeValueMapper
    DIRECTION = Forward (Source To Destination)
    LUT = 0,7,1,8,2,9,3,10,4,11,5,12
    SRC = gz_Laermempfindlichkeit
    VAL_ATTR = LAERMES
    -> AttributeValueMapper_4
Note: KANTART mappen. / Interlis-Codelisten starten bei 0, / GeoDB-Wertetabellen bei 1! / Achtung: Bern hat zwei zusätliche / Werte!!!
AttributeValueMapper_4
    DIRECTION = Forward (Source To Destination)
    LUT = 0,W1,1,W2,2,W3,3,W4,4,W5,5,W6plus,6,WE,7,FH,8,M2,9,M3,10,M4,11,M5,12,M6plus,13,ME,14,KS,15,KL,16,HT,17,WEZ,18,B_E,19,BH,20,A,21,ZOEN,22,SKI,23,ZSF,24,GR,25,GB,26,LWZ,27,ILW,28,AA,29,ZMN,30,UEO,31,ZPP,32,SBV,33,USP,34,Uebrige
    SRC = zt_KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Zero or One (1:0..1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_NPZONET
    JOINED -> AttributeValueMapper_23
Note: NZ_TYP mappen.
AttributeValueMapper_23
    DIRECTION = Forward (Source To Destination)
    LUT = 0,unbekannt,1,Wohnzone (W),10,Freifläche A* (Zone für priv. Bauten + Anl. im allg. Int. FA*),11,Freifläche B* (Zone für priv. Bauten + Anl. im allg. Int. FB*),12,Freifläche C* (Zone für priv. Bauten + Anl. im allg. Int. FC*),13,Freifläche D* (Zone für priv. Bauten + Anl. im allg. Int. FD*),14,Schutzzone A (SZA) Landschafts- + Ortsbildschutzareal,15,Schutzzone B (SZB) Landschafts- + Ortsbildschutzareal,16,Schutzzone C (SZC) Naturschutzareal,17,Obere Altstadt, Zone mit Planungspflicht,18,Untere Altstadt und Wohngebiet Matte,19,Gewerbegebiete Matte, Zone mit Planungspflicht,2,Gemischte Wohnzone (WG),20,Landwirtschaftszone,21,Weilerzone,22,Übriges Gebiet: Wald,23,Übriges Gebiet: Gewässer,24,Übriges Gebiet: Verkehrsfläche ausserhalb Siedlungsgebiet,25,Überbauungsordnung,26,Zone mit Planungspflicht,27,Übriges Gebiet: andere,3,Kernzone (K),4,Dienstleistungszone (D),5,Industrie- und Gewerbezone (IG),6,Freifläche A (Zone für öff. Nutzungen FA),7,Freifläche B (Zone für öff. Nutzungen FB),8,Freifläche C (Zone für öff. Nutzungen FC),9,Freifläche D (Zone für öff. Nutzungen FD)
    SRC = zt_Nutzungszone
    VAL_ATTR = NZ_TYP
    -> AttributeValueMapper_22
Note: BK_TYP mappen
AttributeValueMapper_22
    DIRECTION = Forward (Source To Destination)
    LUT = 0,unbekannt,1,Bauklasse 1,10,Obere Altstadt, Zone mit Planungspflicht,11,Untere Altstadt und Wohngebiet Matte,12,Gewerbegebiete Matte, Zone mit Planungspflicht,13,Landwirtschaftszone,14,Weilerzone,15,Übriges Gebiet: Wald,16,Übriges Gebiet: Gewässer,17,Übriges Gebiet: Verkehrsfläche ausserhalb Siedlungsgebiet,18,Überbauungsordnung,19,Zone mit Planungspflicht,20,Übriges Gebiet: andere,2,Bauklasse 2,3,Bauklasse 3,4,Bauklasse 4,5,Bauklasse 5,6,Bauklasse 6,7,Bauklasse E, Erhaltung der best. Bebauungsstruktur,8,Festlegung der Bebauung mittels spezieller Vorschriften,9,Zone im öffentlichen Interesse
    SRC = zt_Bauklasse
    VAL_ATTR = BK_TYP
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          nz = feature.getAttribute('zt_Nutzungszone')
          filename = 'nz' + unicode(nz) + '.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> AttributeCreator_2
Note: EIB_AUSSAGE
AttributeCreator_2
    ATTR_LIST = EIB_AUSSAGE_DE,@Value(NZ_TYP),EIB_AUSSAGE_FR,@Value(NZ_TYP)
    -> InlineQuerier [ZONE]
Alle_Aemter (input)
    -> AttributeKeeper
AttributeKeeper
    KEEP_ATTRS = AMT_XTF_ID,AMTNAME,UID_AMT,AMTIMWEB,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeKeeper_5
    JOIN -> AttributeKeeper_6
    JOIN -> AttributeKeeper_8
    JOIN -> AttributeKeeper_9
    JOIN -> AttributeKeeper_10
AttributeKeeper_8
    KEEP_ATTRS = DATENVERW,ZUSTAENDIG,BEZ,BESCHRIEB,BR_NUTZART,ZONENABK,GRUENFZ,FLMASS,BR_NMASS,NZ,BEMERK,INKRAFT,PLANBESCHR,GENEHM,DARST_C_NZ,DARST_C_BK,RVS_ID,QUALITAET,VERBINDLKT,NZ_ART,LAERMES,KANTART,BUNDESART,NZ_TYP,BK_TYP
    -> GNNUTZBK (output)
GNNUTZBK (output)
AttributeKeeper_6
    KEEP_ATTRS = DAR_OID,EIB_SORT,STH_ID,EIB_XTF_ID,filecopy_dest_dataset,EIB_PUBLIZIERTAB,filecopy_source_dataset,RES_ID,EIB_OID,VERBINDLKT,EIB_ARTCODE,EIB_AUSSAGE_FR,EIB_LEGENDESYMBOL_DE,EIB_AUSSAGE_DE,EIB_LEGENDESYMBOL_FR
    -> AttributeFilter_2
Note: Nur Festlegungen kommen / in die Transferstruktur
AttributeFilter_2
    ATTR_NAME = VERBINDLKT
    ATTR_VALUES = <EMPTY>,<MISSING>,<NULL>,<UNFILTERED>,3
    3 -> AttributeRemover
AttributeRemover
    REMOVE_ATTRS = VERBINDLKT
    -> EIGENTUMSBESCHRAENKUNG (output)
EIGENTUMSBESCHRAENKUNG (output)
AttributeKeeper_9
    KEEP_ATTRS = RES_ID,FLA_OID,EIB_OID,FLA_PUBLIZIERTAB,VERBINDLKT
    -> AttributeFilter_3
Note: Nur Festlegungen kommen / in die Transferstruktur
AttributeFilter_3
    ATTR_NAME = VERBINDLKT
    ATTR_VALUES = <EMPTY>,<MISSING>,<NULL>,<UNFILTERED>,3
    3 -> AttributeRemover_2
AttributeRemover_2
    REMOVE_ATTRS = VERBINDLKT
    -> FLAECHE (output)
FLAECHE (output)
AttributeKeeper_10
    KEEP_ATTRS = EIB_XTF_ID,EIB_OID,VERBINDLKT
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> VerwendeteAemter (output)
VerwendeteAemter (output)
GN_ZonentypRV (input)
    -> AttributeKeeper_4
AttributeKeeper_4
    KEEP_ATTRS = rv_xtf_id,rv_Typ,rv_Vorschrift,rv_ArtikelNr
    -> AttributeKeeper_7
AttributeKeeper_7
    KEEP_ATTRS = rv_Typ,rv_Vorschrift,rv_ArtikelNr
    -> AttributeRenamer_3
AttributeRenamer_3
    ATTR_LIST = rv_ArtikelNr,HIV_ARTNR,"",rv_Vorschrift,Vorschrift,""
    -> FeatureMerger_2 [REQUESTOR]
FeatureMerger_2
    IGNORE_NULLS = Yes
    JOIN_KEYS = @Value(rv_Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeRemover_5
AttributeRemover_5
    REMOVE_ATTRS = rv_Typ,VERBINDLKT
    -> HINVOR (output)
HINVOR (output)

FME custom transformer NH_NaturHeimatSchutz

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- DATENVERWALTUNGSSTELLE = @Value(Datenverwaltungsstelle)   # Datenverwaltungsstelle
- ZUSTAENDIGESTELLE = @Value(ZustaendigeStelle)   # ZustaendigeStelle
- QUALITAET = @Value(Qualitaet)   # Qualitaet
- TYP = @Value(Typ)   # Typ
- ORI = @Value(Ori)   # Ori
- BEDEUTUNG = @Value(Bedeutung)   # Bedeutung
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- SCHUTZGRAD = @Value(Schutzgrad)   # Schutzgrad
- VORSCHRIFT = @Value(Vorschrift)   # Vorschrift

NH_FlaechenelementNHS (input)
    -> UUIDGenerator
Note: FLA_OID
UUIDGenerator
    UUID_ATTR = FLA_OID
    -> AttributeRemover
NH_LinienelementNHS (input)
    -> UUIDGenerator_2
Note: LIN_OID
UUIDGenerator_2
    UUID_ATTR = LIN_OID
    -> AttributeRemover
NH_PunktelementNHS (input)
    -> UUIDGenerator_3
Note: PUN_OID
UUIDGenerator_3
    UUID_ATTR = PUN_OID
    -> AttributeRemover
AttributeRemover
    REMOVE_ATTRS = Bezeichnung,KantArt,xtf_id,Abkuerzung,Datenverwaltungsstelle,ZustaendigeStelle,Typ,Bedeutung,Bemerkung,DarstellungCode,Planbeschriftung,ArtikelNr,Verbindlichkeit,Schutzgrad
    -> FeatureMerger [REQUESTOR]
NH_NHSchutz (input)
    -> UUIDGenerator_4
Note: EIB_OID
UUIDGenerator_4
    UUID_ATTR = EIB_OID
    -> AttributeRenamer
AttributeRenamer
    ATTR_LIST = xtf_id,EIB_XTF_ID,""
    -> AttributeRemover_2
AttributeRemover_2
    REMOVE_ATTRS = Objekt,Beschrieb,Qualitaet,Typ,Ori,Inkraftsetzung,Genehmigung,ArtikelNr
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,LINIENABK,"",DarstellungCode,DARST_C,"",Datenverwaltungsstelle,DATENVERW,"",ZustaendigeStelle,ZUSTAENDIG,"",Ori,ORI,""
    -> AttributeCreator
AttributeCreator
    ATTR_LIST = RVS_ID,@Value(EIB_OID),EIB_AUSSAGE_DE,@Value(BEZ),EIB_AUSSAGE_FR,@Value(BEZ),EIB_ARTCODE,@Value(LINIENABK),PUNKTABK,@Value(LINIENABK),ZONENABK,@Value(LINIENABK),EIB_SORT,@Evaluate(400+@int(@Value(KantArt))),RES_ID,1,FLA_PUBLIZIERTAB,@Value(EIB_PUBLIZIERTAB),LIN_PUBLIZIERTAB,@Value(EIB_PUBLIZIERTAB),PUN_PUBLIZIERTAB,@Value(EIB_PUBLIZIERTAB)
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: SCHUTZG mappen. / Interlis-Codelisten starten bei 0, / GeoDB-Wertetabellen bei 1!
AttributeValueMapper_4
    DIRECTION = Forward (Source To Destination)
    LUT = 0,1,1,2,2,3,3,4,4,5
    SRC = Schutzgrad
    VAL_ATTR = SCHUTZG
    -> AttributeValueMapper_5
Note: BEDEUT mappen. / Interlis-Codelisten starten bei 0, / GeoDB-Wertetabellen bei 1!
AttributeValueMapper_5
    DIRECTION = Forward (Source To Destination)
    LUT = 0,1,1,2,2,3,3,4,4,5
    SRC = Bedeutung
    VAL_ATTR = BEDEUT
    -> AttributeValueMapper
Note: KANTART mappen. / Interlis-Codelisten starten bei 0, / GeoDB-Wertetabellen bei 1!
AttributeValueMapper
    DIRECTION = Forward (Source To Destination)
    LUT = 0,37,1,38,2,39,3,40,4,41,5,42,6,43,7,44,8,45,9,46,10,47,11,48,12,49,13,50,14,51,15,52,16,53,17,54,18,55,19,56,20,57,21,58,22,59,23,60,24,61,25,62,26,63,27,64,28,65,29,66,30,67,31,68,32,69,33,70,34,71,35,72,36,73,37,74,38,75,39,76,40,77,41,78,42,79,43,80,44,81,45,82,46,83,47,84,48,85,49,86,50,87,51,88,52,89,53,90,54,91,55,92,56,93,57,94,58,95
    SRC = KantArt
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
    JOIN -> AttributeRemover_3
AttributeRemover_3
    REMOVE_ATTRS = xtf_id,Objekt,Qualitaet,Verbindlichkeit,KantArt,Bedeutung,Schutzgrad,_matched_records
    -> FeatureTypeFilter_2
FeatureTypeFilter_2
    ATTRIBUTES = <BLANK>,<UNFILTERED>,DM16NplBE_Bern.Nutzungsplanung.NH_FlaechenelementNHS,DM16NplBE_Bern.Nutzungsplanung.NH_LinienelementNHS,DM16NplBE_Bern.Nutzungsplanung.NH_PunktelementNHS
    DM16NplBE_Bern.Nutzungsplanung.NH_FlaechenelementNHS -> AttributeCreator_3
    DM16NplBE_Bern.Nutzungsplanung.NH_FlaechenelementNHS -> AttributeRemover_8
    DM16NplBE_Bern.Nutzungsplanung.NH_LinienelementNHS -> AttributeCreator_5
    DM16NplBE_Bern.Nutzungsplanung.NH_LinienelementNHS -> AttributeRemover_8
    DM16NplBE_Bern.Nutzungsplanung.NH_PunktelementNHS -> AttributeRemover_8
    DM16NplBE_Bern.Nutzungsplanung.NH_PunktelementNHS -> AttributeCreator_4
AttributeCreator_3
    ATTR_LIST = STH_ID,13,DAR_OID,ch.be.bve.agi.npl.$(BFSNR).13
    -> AttributeRemover_4
    -> UEFL (output)
    -> AttributeFilter_3
UEFL (output)
Note: Nur Festlegungen kommen / in die Transferstruktur
AttributeFilter_3
    ATTR_NAME = VERBINDLKT
    ATTR_VALUES = <EMPTY>,<MISSING>,<NULL>,<UNFILTERED>,3
    3 -> AttributeKeeper
AttributeKeeper
    KEEP_ATTRS = RES_ID,FLA_OID,EIB_OID,FLA_PUBLIZIERTAB
    -> FLAECHE (output)
FLAECHE (output)
AttributeCreator_5
    ATTR_LIST = STH_ID,14,DAR_OID,ch.be.bve.agi.npl.$(BFSNR).14
    -> AttributeRemover_4
    -> UELN (output)
    -> AttributeFilter_5
UELN (output)
Note: Nur Festlegungen kommen / in die Transferstruktur
AttributeFilter_5
    ATTR_NAME = VERBINDLKT
    ATTR_VALUES = <EMPTY>,<MISSING>,<NULL>,<UNFILTERED>,3
    3 -> AttributeKeeper_2
AttributeKeeper_2
    KEEP_ATTRS = LIN_PUBLIZIERTAB,RES_ID,EIB_OID,LIN_OID
    -> LINIE (output)
LINIE (output)
AttributeCreator_4
    ATTR_LIST = STH_ID,15,DAR_OID,ch.be.bve.agi.npl.$(BFSNR).15
    -> AttributeRemover_4
    -> UEPT (output)
    -> AttributeFilter_6
AttributeRemover_4
    REMOVE_ATTRS = FLA_OID,BEZ,BESCHRIEB,DARST_C,INKRAFT,LIN_OID,QUALITAET,BEDEUT,DATENVERW,Vorschrift,LIN_PUBLIZIERTAB,PUN_PUBLIZIERTAB,PUNKTABK,BUNDESART,ZUSTAENDIG,GENEHM,FLA_PUBLIZIERTAB,PLANBESCHR,LINIENABK,ZONENABK,ORI,RVS_ID,KANTART,PUN_OID,BEMERK,SCHUTZG
    -> AttributeFilter_4
Note: Nur Festlegungen kommen / in die Transferstruktur
AttributeFilter_4
    ATTR_NAME = VERBINDLKT
    ATTR_VALUES = <EMPTY>,<MISSING>,<NULL>,<UNFILTERED>,3
    3 -> AttributeRemover_7
AttributeRemover_7
    -> EIGENTUMSBESCHRAENKUNG (output)
EIGENTUMSBESCHRAENKUNG (output)
UEPT (output)
Note: Nur Festlegungen kommen / in die Transferstruktur
AttributeFilter_6
    ATTR_NAME = VERBINDLKT
    ATTR_VALUES = <EMPTY>,<MISSING>,<NULL>,<UNFILTERED>,3
    3 -> AttributeKeeper_3
AttributeKeeper_3
    KEEP_ATTRS = RES_ID,EIB_OID,PUN_OID,PUN_PUBLIZIERTAB
    -> PUNKT (output)
PUNKT (output)
AttributeRemover_8
    REMOVE_ATTRS = EIB_SORT,FLA_OID,EIB_AUSSAGE_DE,BEZ,BESCHRIEB,DARST_C,INKRAFT,LIN_OID,QUALITAET,BEDEUT,DATENVERW,Vorschrift,LIN_PUBLIZIERTAB,PUN_PUBLIZIERTAB,PUNKTABK,BUNDESART,EIB_PUBLIZIERTAB,ZUSTAENDIG,GENEHM,FLA_PUBLIZIERTAB,PLANBESCHR,LINIENABK,ZONENABK,ORI,RVS_ID,EIB_AUSSAGE_FR,RES_ID,KANTART,PUN_OID,BEMERK,SCHUTZG,EIB_ARTCODE
    -> FeatureMerger_2 [SUPPLIER]
AttributeRemover_6
    REMOVE_ATTRS = xtf_id,Objekt,BESCHRIEB,GENEHM,INKRAFT,Qualitaet,FLA_OID,Ori,PUN_OID,LIN_OID,EIB_XTF_ID,Verbindlichkeit,KantArt,LINIENABK,BEZ,Bedeutung,Schutzgrad,PLANBESCHR,BEMERK,DARST_C,EIB_OID,EIB_PUBLIZIERTAB,RVS_ID,EIB_AUSSAGE_DE,EIB_AUSSAGE_FR,EIB_ARTCODE,PUNKTABK,ZONENABK,EIB_SORT,RES_ID,STH_ID,FLA_PUBLIZIERTAB,LIN_PUBLIZIERTAB,PUN_PUBLIZIERTAB,DAR_OID,QUALITAET,VERBINDLKT,SCHUTZG,BEDEUT,KANTART,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
NH_NHSchutzRV (input)
    -> AttributeRemover_5
AttributeRemover_5
    REMOVE_ATTRS = Objekt,Bezeichnung,KantArt,Beschrieb,xtf_id,Abkuerzung,Datenverwaltungsstelle,ZustaendigeStelle,Qualitaet,Ori,Bedeutung,Bemerkung,Inkraftsetzung,DarstellungCode,Planbeschriftung,Genehmigung,Verbindlichkeit,Schutzgrad
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_2
Note: Nur Festlegungen kommen / in die Transferstruktur
AttributeFilter_2
    ATTR_NAME = VERBINDLKT
    ATTR_VALUES = <EMPTY>,<MISSING>,<NULL>,<UNFILTERED>,3
    3 -> AttributeRemover_9
AttributeRemover_9
    REMOVE_ATTRS = Typ,VERBINDLKT
    -> HINVOR (output)
HINVOR (output)

FME custom transformer VE_Vor_Einschraenkung

Parameters:
- TYP = @Value(Typ)   # Typ
- VORSCHRIFT = @Value(Vorschrift)   # Vorschrift
- ARTIKELNR = @Value(ArtikelNr)   # ArtikelNr
- XTF_ID = @Value(xtf_id)   # Xtf Id
- VERBINDLICHKEIT = @Value(Verbindlichkeit)   # Verbindlichkeit
- KANTART = @Value(KantArt)   # KantArt
- GUELTIG_BIS = @Value(Gueltig_bis)   # Gueltig Bis
- BESCHWERDE_HAENGIG = @Value(Beschwerde_haengig)   # Beschwerde Haengig
- ABKUERZUNG = @Value(Abkuerzung)   # Abkuerzung
- PLANBESCHRIFTUNG = @Value(Planbeschriftung)   # Planbeschriftung
- BEZEICHNUNG = @Value(Bezeichnung)   # Bezeichnung
- NUTZUNGSZIFFER = @Value(Nutzungsziffer)   # Nutzungsziffer
- NUTZUNGSZIFFER_ART = @Value(Nutzungsziffer_Art)   # Nutzungsziffer Art
- GRUENFLAECHENZIFFER = @Value(Gruenflaechenziffer)   # Gruenflaechenziffer
- BEMERKUNG = @Value(Bemerkung)   # Bemerkung
- THEMALAUFENDEAENDERUNG = @Value(ThemaLaufendeAenderung)   # ThemaLaufendeAenderung
- DARSTELLUNGCODE = @Value(DarstellungCode)   # DarstellungCode
- DATENVERWALTUNGSSTELLE = @Value(Datenverwaltungsstelle)   # Datenverwaltungsstelle
- ZUSTAENDIGESTELLE = @Value(ZustaendigeStelle)   # ZustaendigeStelle
- OBJEKT = @Value(Objekt)   # Objekt
- GENEHMIGUNG = @Value(Genehmigung)   # Genehmigung
- INKRAFTSETZUNG = @Value(Inkraftsetzung)   # Inkraftsetzung
- BESCHRIEB = @Value(Beschrieb)   # Beschrieb
- QUALITAET = @Value(Qualitaet)   # Qualitaet
- AMT_XTF_ID = @Value(AMT_XTF_ID)   # Amt Xtf Id
- AMTNAME = @Value(AMTNAME)
- UID_AMT = @Value(UID_AMT)   # Uid Amt
- AMTIMWEB = @Value(AMTIMWEB)
- AMT_ID = @Value(AMT_ID)   # Amt Id
- BFSNR =   # BFS-Nummer
- GEODB_DATABASE =   # GeoDB-Database
- GEODB_USERNAME =   # GeoDB-Username
- GEODB_PASSWORD =   # GeoDB-Passwort

VE_Vor_Einschraenkung (input)
    -> AttributeKeeper
AttributeKeeper
    KEEP_ATTRS = xtf_id,Verbindlichkeit,KantArt,Gueltig_bis,Beschwerde_haengig,Abkuerzung,Planbeschriftung,Bezeichnung,Nutzungsziffer,Nutzungsziffer_Art,Gruenflaechenziffer,Bemerkung,ThemaLaufendeAenderung,DarstellungCode,Datenverwaltungsstelle,ZustaendigeStelle
    -> UUIDGenerator
Note: EIB_OID
UUIDGenerator
    UUID_ATTR = EIB_OID
    -> AttributeRenamer
AttributeRenamer
    ATTR_LIST = xtf_id,EIB_XTF_ID,""
    -> AttributeFilter
Note: Nach Festlegung Gemeinde / und Hinweise filtern
AttributeFilter
    ATTR_NAME = Verbindlichkeit
    ATTR_VALUES = <EMPTY>,<MISSING>,<NULL>,<UNFILTERED>,2,3
    2 -> AttributeFilter_2
    3 -> AttributeFilter_2
Note: Nur laufende Änderungen / weiterverarbeiten
AttributeFilter_2
    ATTR_NAME = KantArt
    ATTR_VALUES = <EMPTY>,<MISSING>,<NULL>,<UNFILTERED>,2
    2 -> FeatureMerger [SUPPLIER]
VE_FlaechenelementEinschr (input)
    -> AttributeKeeper_3
AttributeKeeper_3
    KEEP_ATTRS = xtf_id,Objekt,Genehmigung,Inkraftsetzung,Beschrieb,Qualitaet
    -> UUIDGenerator_2
UUIDGenerator_2
    UUID_ATTR = FLA_OID
    -> AttributeRenamer_3
AttributeRenamer_3
    ATTR_LIST = xtf_id,FLA_XTF_ID,""
    -> FeatureMerger [REQUESTOR]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,ZONENABK,"",DarstellungCode,DARST_C,"",Nutzungsziffer,NZ,"",Gruenflaechenziffer,GRUENFZ,"",Datenverwaltungsstelle,DATENVERW,"",ZustaendigeStelle,ZUSTAENDIG,"",KantArt,_kantart,"",Gueltig_bis,VE_GUELTIG,""
    -> AttributeCreator
Note: RES_ID wird absichtlich auf inKraft / gesetzt. Bis der Auszug mit laufenden / Änderungen umgehen kann! / Stattdessen wird bei EIB_AUSSAGE / der String "(projektiert)" angehängt.
AttributeCreator
    ATTR_LIST = RVS_ID,@Value(EIB_OID),EIB_AUSSAGE_DE,@Value(BEZ) (projektiert),EIB_AUSSAGE_FR,@Value(BEZ) (projektiert),EIB_ARTCODE,@Value(ZONENABK),EIB_SORT,@Evaluate(200+@int(@Value(_kantart))),RES_ID,1,STH_ID,13,FLA_PUBLIZIERTAB,@Value(EIB_PUBLIZIERTAB),DAR_OID,ch.be.bve.agi.npl.$(BFSNR).13
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper_4
Note: KANTART mappen. / Interlis-Codelisten starten bei 0, / GeoDB-Wertetabellen bei 1!
AttributeValueMapper_4
    DIRECTION = Forward (Source To Destination)
    LUT = 0,104,1,105,2,106,3,107
    SRC = _kantart
    VAL_ATTR = KANTART
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          kantart = feature.getAttribute('_kantart')
          bez = feature.getAttribute('BEZ')

          filename = 'laufaend.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> AttributeValueMapper
Note: VE_BESCHW mappen
AttributeValueMapper
    DIRECTION = Forward (Source To Destination)
    LUT = 0,1,1,2
    SRC = Beschwerde_haengig
    VAL_ATTR = VE_BESCHW
    -> AttributeValueMapper_5
Note: VE_THEMA mappen
AttributeValueMapper_5
    DIRECTION = Forward (Source To Destination)
    LUT = 0,1,1,2,2,3,3,4,4,5,5,6,6,7
    SRC = ThemaLaufendeAenderung
    VAL_ATTR = VE_THEMA
    -> InlineQuerier [ZONE]
AlleAemter (input)
    -> AttributeKeeper_4
AttributeKeeper_4
    KEEP_ATTRS = AMT_XTF_ID,AMTNAME,UID_AMT,AMTIMWEB,AMT_ID
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeKeeper_5
    JOIN -> AttributeKeeper_6
    JOIN -> AttributeKeeper_7
    JOIN -> AttributeKeeper_9
    JOIN -> AttributeKeeper_10
AttributeKeeper_6
    KEEP_ATTRS = DAR_OID,EIB_SORT,STH_ID,EIB_XTF_ID,filecopy_dest_dataset,EIB_PUBLIZIERTAB,filecopy_source_dataset,RES_ID,EIB_OID,VERBINDLKT,EIB_ARTCODE,EIB_AUSSAGE_FR,EIB_LEGENDESYMBOL_DE,EIB_AUSSAGE_DE,EIB_LEGENDESYMBOL_FR
    -> AttributeFilter_3
AttributeFilter_3
    ATTR_NAME = VERBINDLKT
    ATTR_VALUES = <EMPTY>,<MISSING>,<NULL>,<UNFILTERED>,3
    3 -> AttributeRemover
AttributeRemover
    -> EIGENTUMSBESCHRAENKUNG (output)
EIGENTUMSBESCHRAENKUNG (output)
AttributeKeeper_7
    KEEP_ATTRS = FLA_XTF_ID,RES_ID,FLA_OID,EIB_OID,VERBINDLKT,FLA_PUBLIZIERTAB
    -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_11
AttributeKeeper_11
    KEEP_ATTRS = FLA_XTF_ID,RES_ID,FLA_OID,EIB_OID,FLA_PUBLIZIERTAB
    -> FLAECHE (output)
FLAECHE (output)
AttributeKeeper_10
    KEEP_ATTRS = DATENVERW,ZUSTAENDIG,GENEHM,INKRAFT,BESCHRIEB,VE_GUELTIG,ZONENABK,PLANBESCHR,BEZ,NZ,GRUENFZ,BEMERK,DARST_C,RVS_ID,QUALITAET,VERBINDLKT,NZ_ART,KANTART,BUNDESART,VE_BESCHW,VE_THEMA
    -> UEFL (output)
UEFL (output)
AttributeKeeper_9
    KEEP_ATTRS = EIB_XTF_ID,EIB_OID,VERBINDLKT
    -> FeatureMerger_2 [SUPPLIER]
AttributeKeeper_5
    KEEP_ATTRS = DATENVERW,ZUSTAENDIG
    -> Aggregator_2
Aggregator_2
    ACCUM_ATTRS_NAME = Yes
    GROUP_BY = DATENVERW ZUSTAENDIG
    MODE = Attributes Only
    ORDERED = No
    SEP = ,
    AGGREGATE -> VerwendeteAemter (output)
VerwendeteAemter (output)
VE_Vor_EinschraenkungRV (input)
    -> AttributeKeeper_2
AttributeKeeper_2
    KEEP_ATTRS = Typ,Vorschrift,ArtikelNr
    -> AttributeRenamer_4
AttributeRenamer_4
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_5
Note: Nur Festlegungen kommen / in die Transferstruktur
AttributeFilter_5
    ATTR_NAME = VERBINDLKT
    ATTR_VALUES = <EMPTY>,<MISSING>,<NULL>,<UNFILTERED>,3
    3 -> AttributeKeeper_8
AttributeKeeper_8
    KEEP_ATTRS = HIV_ARTNR,Vorschrift,EIB_XTF_ID,EIB_OID
    -> HINVOR (output)
HINVOR (output)

FME custom transformer HINWEIDOK flachdruecken

HINWEIDOK (input)
    -> InlineQuerier [HINWEIDOK]
Note: SQL-Query stammt aus dem / View VIW_VORCHAIN1 der / Verschnittfunktion
InlineQuerier
    QUERY_DEF:
      VIW_VORCHAIN1,SELECT HINWEIDOK.VOR_OIDURSPRUNG,
        HINWEIDOK.VOR_OIDHINWEIS,
        HINWEIDOK1.VOR_OIDHINWEIS AS VOR_OIDHINWEIS1,
        HINWEIDOK2.VOR_OIDHINWEIS AS VOR_OIDHINWEIS2
      FROM HINWEIDOK
      LEFT JOIN HINWEIDOK HINWEIDOK1
      ON HINWEIDOK.VOR_OIDHINWEIS = HINWEIDOK1.VOR_OIDURSPRUNG
      LEFT JOIN HINWEIDOK HINWEIDOK2
      ON HINWEIDOK1.VOR_OIDHINWEIS = HINWEIDOK2.VOR_OIDURSPRUNG,FIRST
    QUERY_SCHEMA = VIW_VORCHAIN1,VOR_OIDURSPRUNG,text,VOR_OIDHINWEIS,text,VOR_OIDHINWEIS1,text,VOR_OIDHINWEIS2,text
    TABLE_DEF = HINWEIDOK,ARTIKELNR,text,ORDNNR,text,VOR_OIDURSPRUNG,text,VOR_OIDHINWEIS,text
    VIW_VORCHAIN1 -> InlineQuerier_2 [VIW_VORCHAIN1]
Note: SQL-Query stammt aus dem / View VIW_VORCHAIN2 der / Verschnittfunktion
InlineQuerier_2
    QUERY_DEF:
      VIW_VORCHAIN2,  select "VOR_OIDURSPRUNG","OIDFROM","OIDTO" from
      (select
      VOR_OIDURSPRUNG ,VOR_OIDURSPRUNG oidfrom,  VOR_OIDHINWEIS oidto from VIW_VORCHAIN1
      union
      select
      VOR_OIDURSPRUNG,VOR_OIDHINWEIS, VOR_OIDHINWEIS1 from VIW_VORCHAIN1
      union
      select
      VOR_OIDURSPRUNG,VOR_OIDHINWEIS1, VOR_OIDHINWEIS2 from VIW_VORCHAIN1
      )
      where oidfrom is not null and
      oidto is not null;,FIRST
    QUERY_SCHEMA = VIW_VORCHAIN2,VOR_OIDURSPRUNG,text,oidfrom,text,oidto,text
    TABLE_DEF = VIW_VORCHAIN1,VOR_OIDURSPRUNG,text,VOR_OIDHINWEIS,text,VOR_OIDHINWEIS1,text,VOR_OIDHINWEIS2,text
    VIW_VORCHAIN2 -> AttributeRenamer_11
AttributeRenamer_11
    ATTR_LIST = oidto,VOR_OIDHINWEIS,""
    -> AttributeRemover_14
AttributeRemover_14
    REMOVE_ATTRS = oidfrom
    -> HINWEIDOK_flach (output)
HINWEIDOK_flach (output)

FME custom transformer WE_WegRoute

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- PLANBESCHRIFTUNG = @Value(Planbeschriftung)   # Planbeschriftung
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- SCHUTZGRAD = @Value(Schutzgrad)   # Schutzgrad
- OBJEKT = @Value(Objekt)   # Objekt
- TYP = @Value(Typ)   # Typ
- BEDEUTUNG = @Value(Bedeutung)   # Bedeutung
- ZUSTAENDIGESTELLE = @Value(ZustaendigeStelle)   # ZustaendigeStelle
- GENEHMIGUNG = @Value(Genehmigung)   # Genehmigung
- BEZEICHNUNG = @Value(Bezeichnung)   # Bezeichnung
- ART = @Value(Art)   # Art
- VORSCHRIFT = @Value(Vorschrift)   # Vorschrift

WE_FlaechenelementWeg (input)
    -> UUIDGenerator
Note: FLA_OID
UUIDGenerator
    UUID_ATTR = FLA_OID
    -> AttributeRemover
WE_LinienelementWeg (input)
    -> UUIDGenerator_2
Note: LIN_OID
UUIDGenerator_2
    UUID_ATTR = LIN_OID
    -> AttributeRemover
AttributeRemover
    REMOVE_ATTRS = Verbindlichkeit,xtf_id,Planbeschriftung,ArtikelNr,Datenverwaltungsstelle,DarstellungCode,Schutzgrad,Typ,Bedeutung,ZustaendigeStelle,Bezeichnung,Art
    -> FeatureMerger [REQUESTOR]
WE_WegRoute (input)
    -> UUIDGenerator_4
Note: EIB_OID
UUIDGenerator_4
    UUID_ATTR = EIB_OID
    -> AttributeRenamer
AttributeRenamer
    ATTR_LIST = xtf_id,EIB_XTF_ID,""
    -> AttributeRemover_2
AttributeRemover_2
    REMOVE_ATTRS = ArtikelNr,Inkraftsetzung,Qualitaet,Objekt,Typ,Genehmigung
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",Planbeschriftung,PLANBESCHR,"",DarstellungCode,DARST_C,"",Datenverwaltungsstelle,DATENVERW,"",ZustaendigeStelle,ZUSTAENDIG,""
    -> AttributeCreator
AttributeCreator
    ATTR_LIST = RVS_ID,@Value(EIB_OID),EIB_AUSSAGE_DE,@Value(BEZ),EIB_AUSSAGE_FR,@Value(BEZ),EIB_SORT,@Evaluate(500+@int(@Value(Art))),RES_ID,1,FLA_PUBLIZIERTAB,@Value(EIB_PUBLIZIERTAB),LIN_PUBLIZIERTAB,@Value(EIB_PUBLIZIERTAB),EIB_ARTCODE,""
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: SCHUTZG mappen. / Interlis-Codelisten starten bei 0, / GeoDB-Wertetabellen bei 1!
AttributeValueMapper_4
    DIRECTION = Forward (Source To Destination)
    LUT = 0,1,1,2,2,3,3,4,4,5
    SRC = Schutzgrad
    VAL_ATTR = SCHUTZG
    -> AttributeValueMapper_5
Note: BEDEUT mappen. / Interlis-Codelisten starten bei 0, / GeoDB-Wertetabellen bei 1!
AttributeValueMapper_5
    DIRECTION = Forward (Source To Destination)
    LUT = 0,1,1,2,2,3,3,4,4,5
    SRC = Bedeutung
    VAL_ATTR = BEDEUT
    -> AttributeValueMapper
Note: ART mappen. / Interlis-Codelisten starten bei 0, / GeoDB-Wertetabellen bei 1!
AttributeValueMapper
    DIRECTION = Forward (Source To Destination)
    LUT = 0,96,1,97,2,98,3,99,4,100,5,101,6,102,7,103
    SRC = Art
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
    JOIN -> AttributeRemover_3
AttributeRemover_3
    REMOVE_ATTRS = xtf_id,Objekt,Qualitaet,Verbindlichkeit,Art,Bedeutung,Schutzgrad,_matched_records
    -> FeatureTypeFilter
FeatureTypeFilter
    ATTRIBUTES = <BLANK>,<UNFILTERED>,DM16NplBE_Bern.Nutzungsplanung.WE_FlaechenelementWeg,DM16NplBE_Bern.Nutzungsplanung.WE_LinienelementWeg
    DM16NplBE_Bern.Nutzungsplanung.WE_FlaechenelementWeg -> AttributeCreator_3
    DM16NplBE_Bern.Nutzungsplanung.WE_FlaechenelementWeg -> AttributeRemover_8
    DM16NplBE_Bern.Nutzungsplanung.WE_LinienelementWeg -> AttributeCreator_3
    DM16NplBE_Bern.Nutzungsplanung.WE_LinienelementWeg -> AttributeCreator_5
AttributeCreator_3
    ATTR_LIST = STH_ID,13,DAR_OID,ch.be.bve.agi.npl.$(BFSNR).13
    -> AttributeRemover_4
    -> UEFL (output)
    -> AttributeFilter_3
UEFL (output)
Note: Nur Festlegungen kommen / in die Transferstruktur
AttributeFilter_3
    ATTR_NAME = VERBINDLKT
    ATTR_VALUES = <EMPTY>,<MISSING>,<NULL>,<UNFILTERED>,3
    3 -> AttributeKeeper
AttributeKeeper
    KEEP_ATTRS = RES_ID,FLA_OID,EIB_OID,FLA_PUBLIZIERTAB
    -> FLAECHE (output)
FLAECHE (output)
AttributeCreator_5
    ATTR_LIST = STH_ID,14,DAR_OID,ch.be.bve.agi.npl.$(BFSNR).14
    -> AttributeRemover_4
    -> UELN (output)
    -> AttributeFilter_5
AttributeRemover_4
    REMOVE_ATTRS = FLA_OID,BEZ,DARST_C,INKRAFT,LIN_OID,QUALITAET,BEDEUT,DATENVERW,Vorschrift,LIN_PUBLIZIERTAB,BUNDESART,ZUSTAENDIG,GENEHM,FLA_PUBLIZIERTAB,PLANBESCHR,RVS_ID,KANTART,SCHUTZG
    -> AttributeFilter_2
AttributeFilter_2
    ATTR_NAME = VERBINDLKT
    ATTR_VALUES = <EMPTY>,<MISSING>,<NULL>,<UNFILTERED>,3
    3 -> AttributeRemover_7
AttributeRemover_7
    REMOVE_ATTRS = VERBINDLKT
    -> EIGENTUMSBESCHRAENKUNG (output)
EIGENTUMSBESCHRAENKUNG (output)
UELN (output)
Note: Nur Festlegungen kommen / in die Transferstruktur
AttributeFilter_5
    ATTR_NAME = VERBINDLKT
    ATTR_VALUES = <EMPTY>,<MISSING>,<NULL>,<UNFILTERED>,3
    3 -> AttributeKeeper_2
AttributeKeeper_2
    KEEP_ATTRS = LIN_PUBLIZIERTAB,RES_ID,EIB_OID,LIN_OID
    -> LINIE (output)
LINIE (output)
AttributeRemover_8
    REMOVE_ATTRS = EIB_SORT,FLA_OID,EIB_AUSSAGE_DE,BEZ,DARST_C,INKRAFT,LIN_OID,QUALITAET,BEDEUT,DATENVERW,Vorschrift,LIN_PUBLIZIERTAB,BUNDESART,EIB_PUBLIZIERTAB,ZUSTAENDIG,GENEHM,FLA_PUBLIZIERTAB,PLANBESCHR,RVS_ID,EIB_AUSSAGE_FR,RES_ID,KANTART,SCHUTZG,EIB_ARTCODE
    -> FeatureMerger_2 [SUPPLIER]
AttributeRemover_6
    REMOVE_ATTRS = xtf_id,INKRAFT,Qualitaet,Objekt,GENEHM,Vorschrift,LIN_OID,FLA_OID,Verbindlichkeit,EIB_XTF_ID,PLANBESCHR,DARST_C,Schutzgrad,Bedeutung,BEZ,Art,EIB_OID,EIB_PUBLIZIERTAB,RVS_ID,EIB_AUSSAGE_DE,EIB_AUSSAGE_FR,EIB_SORT,RES_ID,FLA_PUBLIZIERTAB,LIN_PUBLIZIERTAB,EIB_ARTCODE,QUALITAET,VERBINDLKT,SCHUTZG,BEDEUT,KANTART,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
WE_WegRouteRV (input)
    -> AttributeRemover_5
AttributeRemover_5
    REMOVE_ATTRS = Verbindlichkeit,xtf_id,Planbeschriftung,Inkraftsetzung,Datenverwaltungsstelle,DarstellungCode,Qualitaet,Schutzgrad,Objekt,Bedeutung,ZustaendigeStelle,Genehmigung,Bezeichnung,Art
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeRemover_9
AttributeRemover_9
    REMOVE_ATTRS = Typ,VERBINDLKT
    -> HINVOR (output)
HINVOR (output)

FME custom transformer GW_Gewaesser

Parameters:
- GEODB_DATABASE =   # GeoDB-Database
- GEODB_USERNAME =   # GeoDB-Username
- GEODB_PASSWORD =   # GeoDB-Passwort
- BFSNR =   # BFS-Nummer
- VERBINDLICHKEIT = @Value(Verbindlichkeit)   # Verbindlichkeit
- XTF_ID = @Value(xtf_id)   # Xtf Id
- PLANBESCHRIFTUNG = @Value(Planbeschriftung)   # Planbeschriftung
- ARTIKELNR = @Value(ArtikelNr)   # ArtikelNr
- INKRAFTSETZUNG = @Value(Inkraftsetzung)   # Inkraftsetzung
- DATENVERWALTUNGSSTELLE = @Value(Datenverwaltungsstelle)   # Datenverwaltungsstelle
- DARSTELLUNGCODE = @Value(DarstellungCode)   # DarstellungCode
- QUALITAET = @Value(Qualitaet)   # Qualitaet
- OBJEKT = @Value(Objekt)   # Objekt
- OEKOMORPH_NATUERLICHKEIT = @Value(Oekomorph_Natuerlichkeit)   # Oekomorph Natuerlichkeit
- TYP = @Value(Typ)   # Typ
- ZUSTAENDIGESTELLE = @Value(ZustaendigeStelle)   # ZustaendigeStelle
- GENEHMIGUNG = @Value(Genehmigung)   # Genehmigung
- BEMERKUNG = @Value(Bemerkung)   # Bemerkung
- BEZEICHNUNG = @Value(Bezeichnung)   # Bezeichnung
- ART = @Value(Art)   # Art
- KULTURHIST_BEDEUTUNG = @Value(Kulturhist_Bedeutung)   # Kulturhist Bedeutung
- VORSCHRIFT = @Value(Vorschrift)   # Vorschrift

GW_FlaechenelementGew (input)
    -> UUIDGenerator
Note: FLA_OID
UUIDGenerator
    UUID_ATTR = FLA_OID
    -> AttributeRemover
GW_LinienelementGew (input)
    -> UUIDGenerator_2
Note: LIN_OID
UUIDGenerator_2
    UUID_ATTR = LIN_OID
    -> AttributeRemover
AttributeRemover
    REMOVE_ATTRS = Verbindlichkeit,xtf_id,Planbeschriftung,ArtikelNr,Datenverwaltungsstelle,DarstellungCode,Oekomorph_Natuerlichkeit,Typ,ZustaendigeStelle,Bemerkung,Bezeichnung,Art,Kulturhist_Bedeutung
    -> FeatureMerger [REQUESTOR]
GW_Gewaesser (input)
    -> UUIDGenerator_4
Note: EIB_OID
UUIDGenerator_4
    UUID_ATTR = EIB_OID
    -> AttributeRenamer
AttributeRenamer
    ATTR_LIST = xtf_id,EIB_XTF_ID,""
    -> AttributeRemover_2
AttributeRemover_2
    REMOVE_ATTRS = ArtikelNr,Inkraftsetzung,Qualitaet,Objekt,Typ,Genehmigung
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Bezeichnung,BEZ,"",Planbeschriftung,PLANBESCHR,"",DarstellungCode,DARST_C,"",Datenverwaltungsstelle,DATENVERW,"",ZustaendigeStelle,ZUSTAENDIG,"",Bemerkung,BEMERK,""
    -> AttributeCreator
AttributeCreator
    ATTR_LIST = RVS_ID,@Value(EIB_OID),EIB_AUSSAGE_DE,@Value(BEZ),EIB_AUSSAGE_FR,@Value(BEZ),EIB_SORT,@Evaluate(600+@int(@Value(Art))),RES_ID,1,FLA_PUBLIZIERTAB,@Value(EIB_PUBLIZIERTAB),LIN_PUBLIZIERTAB,@Value(EIB_PUBLIZIERTAB),EIB_ARTCODE,""
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_4
Note: GW_NAT mappen. / Interlis-Codelisten starten bei 0, / GeoDB-Wertetabellen bei 1!
AttributeValueMapper_4
    DIRECTION = Forward (Source To Destination)
    LUT = 0,1,1,2,2,3,3,4,4,5,5,6
    SRC = Oekomorph_Natuerlichkeit
    VAL_ATTR = GW_NAT
    -> AttributeValueMapper_5
Note: GW_BED mappen. / Interlis-Codelisten starten bei 0, / GeoDB-Wertetabellen bei 1!
AttributeValueMapper_5
    DIRECTION = Forward (Source To Destination)
    LUT = 0,1,1,2,2,3
    SRC = Kulturhist_Bedeutung
    VAL_ATTR = BEDEUT
    -> AttributeValueMapper
Note: ART mappen. / Interlis-Codelisten starten bei 0, / GeoDB-Wertetabellen bei 1!
AttributeValueMapper
    DIRECTION = Forward (Source To Destination)
    LUT = 0,0,1,1
    SRC = Art
    VAL_ATTR = KANTART
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
    JOIN -> AttributeRemover_3
AttributeRemover_3
    REMOVE_ATTRS = xtf_id,Objekt,Qualitaet,Verbindlichkeit,Art,Oekomorph_Natuerlichkeit,Kulturhist_Bedeutung,_matched_records
    -> FeatureTypeFilter
FeatureTypeFilter
    ATTRIBUTES = <BLANK>,<UNFILTERED>,DM16NplBE_Bern.Nutzungsplanung.GW_FlaechenelementGew,DM16NplBE_Bern.Nutzungsplanung.GW_LinienelementGew
    DM16NplBE_Bern.Nutzungsplanung.GW_FlaechenelementGew -> AttributeCreator_3
    DM16NplBE_Bern.Nutzungsplanung.GW_FlaechenelementGew -> AttributeRemover_8
    DM16NplBE_Bern.Nutzungsplanung.GW_LinienelementGew -> AttributeCreator_5
    DM16NplBE_Bern.Nutzungsplanung.GW_LinienelementGew -> AttributeRemover_8
AttributeCreator_3
    ATTR_LIST = STH_ID,13,DAR_OID,ch.be.bve.agi.npl.$(BFSNR).13
    -> AttributeRemover_4
    -> UEFL (output)
    -> AttributeFilter_3
UEFL (output)
Note: Nur Festlegungen kommen / in die Transferstruktur
AttributeFilter_3
    ATTR_NAME = VERBINDLKT
    ATTR_VALUES = <EMPTY>,<MISSING>,<NULL>,<UNFILTERED>,3
    3 -> AttributeKeeper
AttributeKeeper
    KEEP_ATTRS = RES_ID,FLA_OID,EIB_OID,FLA_PUBLIZIERTAB
    -> FLAECHE (output)
FLAECHE (output)
AttributeCreator_5
    ATTR_LIST = STH_ID,14,DAR_OID,ch.be.bve.agi.npl.$(BFSNR).14
    -> AttributeRemover_4
    -> UELN (output)
    -> AttributeFilter_5
AttributeRemover_4
    REMOVE_ATTRS = FLA_OID,BEZ,DARST_C,INKRAFT,LIN_OID,QUALITAET,BEDEUT,DATENVERW,Vorschrift,LIN_PUBLIZIERTAB,BUNDESART,GW_NAT,ZUSTAENDIG,GENEHM,FLA_PUBLIZIERTAB,PLANBESCHR,RVS_ID,KANTART,BEMERK
    -> AttributeFilter_2
AttributeFilter_2
    ATTR_NAME = VERBINDLKT
    ATTR_VALUES = <EMPTY>,<MISSING>,<NULL>,<UNFILTERED>,3
    3 -> AttributeRemover_7
AttributeRemover_7
    REMOVE_ATTRS = VERBINDLKT
    -> EIGENTUMSBESCHRAENKUNG (output)
EIGENTUMSBESCHRAENKUNG (output)
UELN (output)
Note: Nur Festlegungen kommen / in die Transferstruktur
AttributeFilter_5
    ATTR_NAME = VERBINDLKT
    ATTR_VALUES = <EMPTY>,<MISSING>,<NULL>,<UNFILTERED>,3
    3 -> AttributeKeeper_2
AttributeKeeper_2
    KEEP_ATTRS = LIN_PUBLIZIERTAB,RES_ID,EIB_OID,LIN_OID
    -> LINIE (output)
LINIE (output)
AttributeRemover_8
    REMOVE_ATTRS = EIB_SORT,FLA_OID,EIB_AUSSAGE_DE,BEZ,DARST_C,INKRAFT,LIN_OID,QUALITAET,BEDEUT,DATENVERW,Vorschrift,LIN_PUBLIZIERTAB,BUNDESART,EIB_PUBLIZIERTAB,GW_NAT,ZUSTAENDIG,GENEHM,FLA_PUBLIZIERTAB,PLANBESCHR,RVS_ID,EIB_AUSSAGE_FR,RES_ID,KANTART,BEMERK,EIB_ARTCODE
    -> FeatureMerger_2 [SUPPLIER]
AttributeRemover_6
    REMOVE_ATTRS = xtf_id,Objekt,GENEHM,INKRAFT,Qualitaet,LIN_OID,FLA_OID,EIB_XTF_ID,Verbindlichkeit,Art,Oekomorph_Natuerlichkeit,Kulturhist_Bedeutung,BEZ,PLANBESCHR,Bemerkung,DARST_C,EIB_OID,EIB_PUBLIZIERTAB,RVS_ID,EIB_AUSSAGE_DE,EIB_AUSSAGE_FR,EIB_SORT,RES_ID,FLA_PUBLIZIERTAB,LIN_PUBLIZIERTAB,EIB_ARTCODE,QUALITAET,VERBINDLKT,GW_NAT,BEDEUT,KANTART,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
GW_GewaesserRV (input)
    -> AttributeRemover_5
AttributeRemover_5
    REMOVE_ATTRS = Verbindlichkeit,xtf_id,Planbeschriftung,Inkraftsetzung,Datenverwaltungsstelle,DarstellungCode,Qualitaet,Objekt,Oekomorph_Natuerlichkeit,ZustaendigeStelle,Genehmigung,Bemerkung,Bezeichnung,Art,Kulturhist_Bedeutung
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeRemover_9
AttributeRemover_9
    REMOVE_ATTRS = Typ,VERBINDLKT
    -> HINVOR (output)
HINVOR (output)

FME custom transformer UE_Ueberlagerung

Parameters:
- GEODB_DATABASE =   # GeoDB-Database
- GEODB_USERNAME =   # GeoDB-Username
- GEODB_PASSWORD =   # GeoDB-Passwort
- BFSNR =   # BFS-Nummer
- OBJEKT = @Value(Objekt)   # Objekt
- BEZEICHNUNG = @Value(Bezeichnung)   # Bezeichnung
- KANTART = @Value(KantArt)   # KantArt
- BESCHRIEB = @Value(Beschrieb)   # Beschrieb
- XTF_ID = @Value(xtf_id)   # Xtf Id
- ABKUERZUNG = @Value(Abkuerzung)   # Abkuerzung
- NUTZUNGSZIFFER_ART = @Value(Nutzungsziffer_Art)   # Nutzungsziffer Art
- DATENVERWALTUNGSSTELLE = @Value(Datenverwaltungsstelle)   # Datenverwaltungsstelle
- ZUSTAENDIGESTELLE = @Value(ZustaendigeStelle)   # ZustaendigeStelle
- GRUENFLAECHENZIFFER = @Value(Gruenflaechenziffer)   # Gruenflaechenziffer
- QUALITAET = @Value(Qualitaet)   # Qualitaet
- TYP = @Value(Typ)   # Typ
- NUTZUNGSZIFFER = @Value(Nutzungsziffer)   # Nutzungsziffer
- BEMERKUNG = @Value(Bemerkung)   # Bemerkung
- INKRAFTSETZUNG = @Value(Inkraftsetzung)   # Inkraftsetzung
- DARSTELLUNGCODE = @Value(DarstellungCode)   # DarstellungCode
- PLANBESCHRIFTUNG = @Value(Planbeschriftung)   # Planbeschriftung
- GENEHMIGUNG = @Value(Genehmigung)   # Genehmigung
- ARTIKELNR = @Value(ArtikelNr)   # ArtikelNr
- VERBINDLICHKEIT = @Value(Verbindlichkeit)   # Verbindlichkeit
- VORSCHRIFT = @Value(Vorschrift)   # Vorschrift
- LEGEND_BASEURL =
- LEGEND_BASEDIR =
- LEGEND_INPUTDIR =

UE_FlaechenelementUeberl (input)
    -> UUIDGenerator
Note: FLA_OID
UUIDGenerator
    UUID_ATTR = FLA_OID
    -> AttributeRemover_7
AttributeRemover_7
    REMOVE_ATTRS = Bezeichnung,KantArt,xtf_id,Abkuerzung,Nutzungsziffer_Art,Datenverwaltungsstelle,ZustaendigeStelle,Gruenflaechenziffer,Typ,Nutzungsziffer,Bemerkung,DarstellungCode,Planbeschriftung,ArtikelNr,Verbindlichkeit,Vorschrift
    -> FeatureMerger [REQUESTOR]
UE_UeberlagerungZone (input)
    -> UUIDGenerator_2
Note: EIB_OID
UUIDGenerator_2
    UUID_ATTR = EIB_OID
    -> AttributeRenamer
AttributeRenamer
    ATTR_LIST = xtf_id,EIB_XTF_ID,""
    -> AttributeRemover_8
AttributeRemover_8
    REMOVE_ATTRS = Objekt,Beschrieb,Qualitaet,Typ,Inkraftsetzung,Genehmigung,ArtikelNr,Vorschrift
    -> AttributeFilter
Note: Nach Festlegung Gemeinde / und Hinweise filtern
AttributeFilter
    ATTR_NAME = Verbindlichkeit
    ATTR_VALUES = <EMPTY>,<MISSING>,<NULL>,<UNFILTERED>,2,3
    2 -> FeatureMerger [SUPPLIER]
    3 -> FeatureMerger [SUPPLIER]
FeatureMerger
    IGNORE_NULLS = Yes
    JOIN_KEYS = @Value(Objekt) @Value(EIB_XTF_ID) AUTO
    MERGE_TYPE = Attributes Only
    PROCESS_DUPS = No
    SUPPLIERS_FIRST = No
    SUPPLIER_PREFIX_DUMMY = YES
    MERGED -> TimeStamper
TimeStamper
    FMT = FME Date (^Y^m^d)
    TIME_ATTR = EIB_PUBLIZIERTAB
    -> AttributeRenamer_2
AttributeRenamer_2
    ATTR_LIST = Genehmigung,GENEHM,"",Inkraftsetzung,INKRAFT,"",Beschrieb,BESCHRIEB,"",Bezeichnung,BEZ,"",Planbeschriftung,PLANBESCHR,"",Bemerkung,BEMERK,"",Abkuerzung,ZONENABK,"",DarstellungCode,DARST_C,"",Nutzungsziffer,NZ,"",Gruenflaechenziffer,GRUENFZ,"",Datenverwaltungsstelle,DATENVERW,"",ZustaendigeStelle,ZUSTAENDIG,"",KantArt,_kantart,""
    -> AttributeCreator
AttributeCreator
    ATTR_LIST = RVS_ID,@Value(EIB_OID),EIB_AUSSAGE_DE,@Value(BEZ),EIB_AUSSAGE_FR,@Value(BEZ),EIB_ARTCODE,@Value(ZONENABK),EIB_SORT,@Evaluate(200+@int(@Value(_kantart))),RES_ID,1,STH_ID,12,FLA_PUBLIZIERTAB,@Value(EIB_PUBLIZIERTAB),DAR_OID,ch.be.bve.agi.npl.$(BFSNR).12
    -> DateFormatter
DateFormatter
    DATE_ATTR = GENEHM,INKRAFT
    FMT = FME Date (%Y%m%d)
    INVALID_DATE_VALUE = _FME_NO_OP_
    SRCFMT = Unknown - Automatic Detection
    -> AttributeValueMapper_3
Note: QUALITAET mappen / Interlis-Codelisten starten bei 0, / GeoDB-Wertetabellen bei 1!
AttributeValueMapper_3
    DIRECTION = Forward (Source To Destination)
    LUT = 0,1,1,2,2,3,3,4,4,5,5,6,6,7,7,8,8,9,9,10,10,11
    SRC = Qualitaet
    VAL_ATTR = QUALITAET
    -> AttributeValueMapper_2
Note: VERBINDLKT mappen / Interlis-Codelisten starten bei 0, / GeoDB-Wertetabellen bei 1!
AttributeValueMapper_2
    DIRECTION = Forward (Source To Destination)
    LUT = 0,1,1,2,2,3,3,4
    SRC = Verbindlichkeit
    VAL_ATTR = VERBINDLKT
    -> AttributeValueMapper_6
Note: NZ_ART mappen / Interlis-Codelisten starten bei 0, / GeoDB-Wertetabellen bei 1!
AttributeValueMapper_6
    DIRECTION = Forward (Source To Destination)
    LUT = 0,1,1,2,2,3,3,4,4,5,5,6
    SRC = Nutzungsziffer_Art
    VAL_ATTR = NZ_ART
    -> AttributeValueMapper_4
Note: KANTART mappen. / Interlis-Codelisten starten bei 0, / GeoDB-Wertetabellen bei 1!
Note: TODO: Mapping Gewässer
AttributeValueMapper_4
    DIRECTION = Forward (Source To Destination)
    LUT = 0,108,1,2,2,3,3,4,4,5,5,6,6,7,7,8,8,9,9,10,10,11,11,12,12,13,13,14,14,15,15,16,16,17,17,19
    SRC = _kantart
    VAL_ATTR = KANTART
    -> PythonCaller
Note: Legendenbilder
PythonCaller
    NEW_ATTRIBUTES = EIB_LEGENDESYMBOL_DE EIB_LEGENDESYMBOL_FR filecopy_source_dataset filecopy_dest_dataset
    PYTHONSOURCE:
      import fmeobjects
      import os

      def processFeature(feature):

          kantart = feature.getAttribute('_kantart')
          bez = feature.getAttribute('BEZ')

          filename = 'noueberlagerung.png'
          if kantart == '3':
              filename = 'sp.png'
          elif kantart == '4':
              filename = 'zppspez.png'
          elif kantart == '6':
              filename = 'les6.png'
          elif kantart == '7':
              filename = 'les7.png'
          elif kantart == '8':
              filename = 'les8.png'
          elif kantart == '9':
              filename = 'les9.png'
          elif kantart == '10':
              filename = 'les10.png'
          elif kantart == '11':
              filename = 'les11.png'
          elif kantart == '12':
              filename = 'geferh.png'
          elif kantart == '13':
              filename = 'gefmit.png'
          elif kantart == '14':
              filename = 'gefger.png'
          elif kantart == '15':
              filename = 'gefres.png'
          elif kantart == '16':
              filename = 'gefhin.png'
          elif kantart == '17' and bez.startswith('Planungsgebiet'):
              filename = 'lespg.png'
          elif kantart == '17' and bez.startswith('USP'):
              filename = 'usp.png'
          elif kantart == '17' and bez.startswith('Aaretal'):
              filename = 'asg.png'
          elif kantart == '17' and bez.startswith('Altstadt'):
              filename = 'ap.png'

          outputURL = FME_MacroValues['LEGEND_BASEURL'] + filename

          inputFile = os.path.join(FME_MacroValues['LEGEND_INPUTDIR'], filename)
          inputFile = inputFile.replace('\\','/')

          outputDir = FME_MacroValues['LEGEND_BASEDIR'].replace('\\','/')

          feature.setAttribute('EIB_LEGENDESYMBOL_DE', outputURL)
          feature.setAttribute('EIB_LEGENDESYMBOL_FR', outputURL)
          feature.setAttribute('filecopy_source_dataset', inputFile)
          feature.setAttribute('filecopy_dest_dataset', outputDir)
    PYTHONSYMBOL = processFeature
    -> Joiner
Note: BUNDESART mappen
Joiner
    ADDED_FIELDS = BUNDESART
    CACHE_SIZE = 5000
    DATASET = $(GEODB_DATABASE)
    FORMAT = ORACLE8I_DB
    JOIN_KEYS = KANTART KANTART
    MATCH_RULE_DISPLAY = Must Match Exactly One (1:1)
    ORACLE8I_DB_PASSWORD = $(GEODB_PASSWORD)
    ORACLE8I_DB_PERSISTENT_CONNECTION = YES
    ORACLE8I_DB_REMOVE_SCHEMA_QUALIFIER = NO
    ORACLE8I_DB_SERVER_TYPE = ORACLE8i
    ORACLE8I_DB_SHOW_SYSTEM_TABLES = NO
    ORACLE8I_DB_USER_NAME = $(GEODB_USERNAME)
    PREFETCH_EXHAUSTIVE = Yes
    TABLE = GEODB.NUPLA_UEARTKTT
    JOINED -> InlineQuerier [ZONE]
Alle_Aemter (input)
    -> InlineQuerier [AMT]
Note: AMT joinen
InlineQuerier
    QUERY_DEF:
      JOIN,SELECT z.xtf_id, a1.AMT_ID as DATENVERW, a2.AMT_ID as ZUSTAENDIG, z.fme_feature_content
      FROM ZONE as z
      LEFT JOIN AMT as a1 ON z.DATENVERW=a1.AMT_XTF_ID
      LEFT JOIN AMT as a2 ON z.ZUSTAENDIG=a2.AMT_XTF_ID,FIRST
    QUERY_SCHEMA = JOIN,xtf_id,text,DATENVERW,text,ZUSTAENDIG,text,ZONE.fme_feature_content,fme_feature_content
    TABLE_DEF = AMT,AMT_XTF_ID,text,AMT_ID,text,ZONE,xtf_id,text,DATENVERW,text,ZUSTAENDIG,text
    JOIN -> AttributeRemover_6
    JOIN -> AttributeRemover
AttributeRemover
    REMOVE_ATTRS = xtf_id,Objekt,Qualitaet,Verbindlichkeit,KantArt,Nutzungsziffer_Art,_matched_records
    -> AttributeRangeFilter
AttributeRangeFilter
    IN_ATTR = KANTART
    LUT = 13,17,Gefahrengebiete,7,12,Laermempfindlichkeitsstufen
    Gefahrengebiete -> Attribute_Renamer_Gefahren
    Laermempfindlichkeitsstufen -> Attribute_Renamer_LES
    <UNFILTERED> -> Tester
Attribute_Renamer_Gefahren: AttributeCreator
    ATTR_LIST = STH_ID,13,DAR_OID,ch.be.bve.agi.npl.$(BFSNR).13
    -> FeatureHolder_2
Note: LES-Planungsgebiete filtern
Tester
    BOOL_OP = AND
    TEST_CLAUSE:
      TEST @Value(KANTART) = 19
      TEST @Value(BEZ) BEGINS_WITH Planungsgebiet
    PASSED -> Attribute_Renamer_LES
    FAILED -> TestFilter
Note: Altstadtperimeter und ZPP Spez / kommen in GNZPPUEO
TestFilter
    DEFAULT_VALUE = ALLEANDEREN
    TEST_LIST:
      BOOL_OP,AND,COMPOSITE_TEST,<Unused>,TEST_CLAUSE,"TEST @Value(KANTART) = 19
      TEST @Value(BEZ) BEGINS_WITH Altstadtperimeter",ALTSTADTPERIMETER,BOOL_OP,AND,COMPOSITE_TEST,<Unused>,TEST_CLAUSE,"TEST @Value(_kantart) = 4
      TEST @Value(BEZ) BEGINS_WITH ZPP",ZPPSPEZ
    ALTSTADTPERIMETER -> AttributeCreator_2
    ZPPSPEZ -> AttributeCreator_2
    ALLEANDEREN -> FeatureHolder_2
AttributeCreator_2
    ATTR_LIST = STH_ID,16,DAR_OID,ch.be.bve.agi.npl.$(BFSNR).16,ZONENABK,ZPP Spez
    -> AttributeRemover_2
    -> AttributeKeeper
    -> AttributeKeeper_2
AttributeKeeper_2
    KEEP_ATTRS = DATENVERW,ZUSTAENDIG,BESCHRIEB,INKRAFT,GENEHM,BEZ,ZONENABK,GRUENFZ,NZ,BEMERK,DARST_C,PLANBESCHR,RVS_ID,QUALITAET,VERBINDLKT,NZ_ART
    -> AttributeCreator_3
AttributeCreator_3
    ATTR_LIST = KANTART,ZPP,BUNDESART,1.19
    -> GNZPPUEO (output)
GNZPPUEO (output)
FeatureHolder_2
    -> AttributeRemover_2
    -> UEFL (output)
    -> AttributeKeeper
UEFL (output)
Attribute_Renamer_LES: AttributeCreator
    ATTR_LIST = STH_ID,150,DAR_OID,ch.be.bve.agi.npl.$(BFSNR).150
    -> AttributeRemover_2
    -> UELARMES (output)
    -> AttributeKeeper
AttributeRemover_2
    REMOVE_ATTRS = FLA_OID,GRUENFZ,_kantart,BEZ,BESCHRIEB,DARST_C,INKRAFT,QUALITAET,DATENVERW,NZ_ART,BUNDESART,ZUSTAENDIG,GENEHM,FLA_PUBLIZIERTAB,PLANBESCHR,NZ,ZONENABK,RVS_ID,KANTART,BEMERK
    -> AttributeRemover_3
    -> AttributeFilter_2
Note: Nur Festlegungen kommen / in die Transferstruktur
AttributeFilter_2
    ATTR_NAME = VERBINDLKT
    ATTR_VALUES = <EMPTY>,<MISSING>,<NULL>,<UNFILTERED>,3
    3 -> AttributeRemover_5
AttributeRemover_5
    REMOVE_ATTRS = VERBINDLKT
    -> EIGENTUMSBESCHRAENKUNG (output)
EIGENTUMSBESCHRAENKUNG (output)
AttributeRemover_3
    REMOVE_ATTRS = _kantart,EIB_PUBLIZIERTAB,EIB_AUSSAGE_DE,EIB_AUSSAGE_FR,EIB_ARTCODE,EIB_SORT,RES_ID,STH_ID,DAR_OID,EIB_LEGENDESYMBOL_DE,EIB_LEGENDESYMBOL_FR,filecopy_source_dataset,filecopy_dest_dataset
    -> FeatureMerger_2 [SUPPLIER]
AttributeKeeper
    KEEP_ATTRS = RES_ID,FLA_OID,EIB_OID,FLA_PUBLIZIERTAB,VERBINDLKT
    -> AttributeFilter_3
Note: Nur Festlegungen kommen / in die Transferstruktur
AttributeFilter_3
    ATTR_NAME = VERBINDLKT
    ATTR_VALUES = <EMPTY>,<MISSING>,<NULL>,<UNFILTERED>,3
    3 -> AttributeRemover_9
AttributeRemover_9
    REMOVE_ATTRS = VERBINDLKT
    -> FLAECHE (output)
FLAECHE (output)
UELARMES (output)
AttributeRemover_6
    REMOVE_ATTRS = xtf_id,Objekt,BEZ,KantArt,BESCHRIEB,ZONENABK,Nutzungsziffer_Art,GRUENFZ,Qualitaet,Typ,NZ,BEMERK,INKRAFT,DARST_C,PLANBESCHR,GENEHM,ArtikelNr,Verbindlichkeit,Vorschrift,FLA_OID,EIB_XTF_ID,EIB_OID,EIB_PUBLIZIERTAB,RVS_ID,EIB_AUSSAGE_DE,EIB_AUSSAGE_FR,EIB_ARTCODE,EIB_SORT,RES_ID,STH_ID,FLA_PUBLIZIERTAB,DAR_OID,QUALITAET,VERBINDLKT,NZ_ART,KANTART,BUNDESART,_matched_records
    -> Aggregator_2
Aggregator_2
    ACCUM_ATTRS_NAME = Yes
    GROUP_BY = DATENVERW ZUSTAENDIG
    MODE = Attributes Only
    ORDERED = No
    SEP = ,
    AGGREGATE -> Verwendete_Aemter (output)
Verwendete_Aemter (output)
UE_UeberlagerungZoneRV (input)
    -> AttributeRemover_4
AttributeRemover_4
    REMOVE_ATTRS = Objekt,Bezeichnung,KantArt,Beschrieb,xtf_id,Abkuerzung,Nutzungsziffer_Art,Datenverwaltungsstelle,ZustaendigeStelle,Gruenflaechenziffer,Qualitaet,Nutzungsziffer,Bemerkung,Inkraftsetzung,DarstellungCode,Planbeschriftung,Genehmigung,Verbindlichkeit
    -> AttributeRenamer_3
AttributeRenamer_3
    ATTR_LIST = ArtikelNr,HIV_ARTNR,""
    -> FeatureMerger_2 [REQUESTOR]
FeatureMerger_2
    IGNORE_NULLS = Yes
    JOIN_KEYS = @Value(Typ) @Value(EIB_XTF_ID) AUTO
    MERGE_TYPE = Attributes Only
    PROCESS_DUPS = No
    SUPPLIERS_FIRST = No
    SUPPLIER_PREFIX_DUMMY = YES
    MERGED -> AttributeFilter_4
Note: Nur Festlegungen kommen / in die Transferstruktur
AttributeFilter_4
    ATTR_NAME = VERBINDLKT
    ATTR_VALUES = <EMPTY>,<MISSING>,<NULL>,<UNFILTERED>,3
    3 -> AttributeKeeper_3
AttributeKeeper_3
    KEEP_ATTRS = HIV_ARTNR,Vorschrift,EIB_XTF_ID,EIB_OID
    -> HINVOR (output)
HINVOR (output)
