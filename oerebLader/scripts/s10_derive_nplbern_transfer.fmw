FME workspace s10_derive_nplbern_transfer.fmw

Parameters:
- GEODB_DATABASE =   # GeoDB-Database
- GEODB_USERNAME =   # GEODB-Username
- GEODB_PASSWORD =   # GEODB-Passwort
- OEREB_DATABASE =   # OEREB-Database
- OEREB_USERNAME =   # OEREB-Username
- OEREB_PASSWORD =   # OEREB-Passwort
- DestDataset_FFS = D:\ilitest\bern_double_eib_oid.ffs   # Destination FME Feature Store (FFS) File
- BFSNR =   # BFS-Nr
- LIEFEREINHEIT =   # Liefereinheit
- LOGFILE =   # Logfile

Readers:
- GEODATABASE_SDE_1: GEODATABASE_SDE from sde

Writers:
- GEODATABASE_SDE_2: GEODATABASE_SDE to sde
- ORACLE8I_DB_1: ORACLE8I_DB to $(OEREB_DATABASE)
- FFS_1: FFS to $(DestDataset_FFS)

Note: GEODB.NPL_GNGZ / (für Bern nicht relevant)
GEODB.NPL_GNGZ (reader GEODATABASE_SDE_1) [off]
    attributes: geodb_oid integer, OBJECTID integer, BFSNR smallint, REL_ID char(100), VERBINDLKT char(100), ZONENABK char(12), ZONENCODE char(12), ZONENNAME char(60), KANTZONE char(100), SHAPE.AREA double, SHAPE.LEN double
    -> AttributeRenamer_3
AttributeRenamer_3
    ATTR_LIST = ZONENABK,EIB_ARTCODE,"",ZONENNAME,EIB_AUSSAGE_DE,"",REL_ID,EIB_OID,""
    -> AttributeCreator_3
AttributeCreator_3
    ATTR_LIST = RES_ID,1,DAR_OID,GEODB.NPL_GNGZ_$(BFSNR),THE_ID,1
    -> UUIDGenerator
Note: GEODB.NPL_UEUZ
GEODB.NPL_UEUZ (reader GEODATABASE_SDE_1)
    attributes: BFSNR smallint, REL_ID char(100), KANTART char(100), ZONENABK char(12), BESCHRIEB char(80)
    -> AttributeRenamer
AttributeRenamer
    ATTR_LIST = REL_ID,EIB_OID,"",ZONENABK,EIB_ARTCODE,""
    -> PythonCaller
PythonCaller
    PYTHONSOURCE:
      import fmeobjects

      def getAussageUEUZ(feature):
          beschrieb = feature.getAttribute("BESCHRIEB")
          kantart = feature.getAttribute("KANTART")
          aussage = kantart

          if beschrieb is not None and beschrieb != "":
              aussage = beschrieb

          feature.setAttribute("EIB_AUSSAGE_DE", aussage)
    PYTHONSYMBOL = getAussageUEUZ
    NEW_ATTRIBUTES = EIB_AUSSAGE_DE
    -> AttributeCreator_4
AttributeCreator_4
    ATTR_LIST = RES_ID,1,DAR_OID,GEODB.NPL_UEUZ_$(BFSNR),THE_ID,1
    -> AttributeValueMapper_5
AttributeValueMapper_5
    DIRECTION = Forward (Source To Destination)
    VAL_ATTR = EIB_SORT
    DEFAULT_VALUE = 1001
    LUT = USP,1000,Aaretal-SG,1002
    SRC = EIB_ARTCODE
    -> UUIDGenerator
Note: GEODB.NPL_UELAERM
GEODB.NPL_UELAERM (reader GEODATABASE_SDE_1)
    attributes: BFSNR smallint, REL_ID char(100), KANTART char(100), ZONENABK char(12)
    -> AttributeRenamer_4
AttributeRenamer_4
    ATTR_LIST = REL_ID,EIB_OID,"",KANTART,EIB_AUSSAGE_DE,"",ZONENABK,EIB_ARTCODE,""
    -> AttributeCreator_5
AttributeCreator_5
    ATTR_LIST = RES_ID,1,DAR_OID,GEODB.NPL_UELAERM_$(BFSNR),THE_ID,15
    -> AttributeValueMapper_4
AttributeValueMapper_4
    DIRECTION = Forward (Source To Destination)
    VAL_ATTR = EIB_SORT
    DEFAULT_VALUE = 105
    LUT = ES I,100,ES II,101,ES III,102,ES IV,103
    SRC = EIB_ARTCODE
    -> UUIDGenerator
Note: GEODB.NPL_UEUL
GEODB.NPL_UEUL (reader GEODATABASE_SDE_1)
    attributes: BFSNR smallint, REL_ID char(100), KANTART char(100), LINIENABK char(12), BESCHRIEB char(80)
    -> AttributeRenamer_5
AttributeRenamer_5
    ATTR_LIST = REL_ID,EIB_OID,"",LINIENABK,EIB_ARTCODE,""
    -> PythonCaller_2
PythonCaller_2
    PYTHONSOURCE:
      import fmeobjects

      def getAussageUEUL(feature):
          beschrieb = feature.getAttribute("BESCHRIEB")
          kantart = feature.getAttribute("KANTART")
          aussage = kantart

          if beschrieb is not None and beschrieb != "":
              aussage = beschrieb

          feature.setAttribute("EIB_AUSSAGE_DE", aussage)
    PYTHONSYMBOL = getAussageUEUL
    NEW_ATTRIBUTES = EIB_AUSSAGE_DE
    -> AttributeCreator_6
AttributeCreator_6
    ATTR_LIST = RES_ID,1,DAR_OID,GEODB.NPL_UEUL_$(BFSNR),THE_ID,1
    -> AttributeValueMapper_6
AttributeValueMapper_6
    DIRECTION = Forward (Source To Destination)
    VAL_ATTR = EIB_SORT
    DEFAULT_VALUE = 2000
    LUT = Baulinie,2000,Arkadenbaulinie,2001,Baulinie für Umbauten,2002,Baulinie für unterirdische Bauten,2003,Baulinie mit bes. Bestimmungen,2004,Erdgeschossbaulinie,2005,Gestaltungsbaulinie,2006,Hauptbaulinie,2007,Hilfsbaulinie,2008,Hofbaulinie,2009,Laubenfluchtlinie,2010,Parterrebaulinie,2011,Sockelbaulinie,2012,Strassenbaulinie,2013,Vordachbaulinie,2014,seitliche und rückwärtige Baulinie,2015
    SRC = BESCHRIEB
    -> UUIDGenerator
Note: GEODB.NPL_UEWAAB
GEODB.NPL_UEWAAB (reader GEODATABASE_SDE_1)
    attributes: BFSNR smallint, REL_ID char(100), KANTART char(100), LINIENABK char(12)
    -> AttributeRenamer_6
AttributeRenamer_6
    ATTR_LIST = REL_ID,EIB_OID,"",KANTART,EIB_AUSSAGE_DE,"",LINIENABK,EIB_ARTCODE,""
    -> AttributeCreator_7
AttributeCreator_7
    ATTR_LIST = RES_ID,1,DAR_OID,GEODB.NPL_UEWAAB_$(BFSNR),THE_ID,17,EIB_SORT,100
    -> UUIDGenerator
Note: GEODB.NPL_VEFE
GEODB.NPL_VEFE (reader GEODATABASE_SDE_1)
    attributes: BFSNR smallint, REL_ID char(100), KANTART char(100), BESCHRIEB char(80)
    -> AttributeRenamer_7
AttributeRenamer_7
    ATTR_LIST = REL_ID,EIB_OID,"",BESCHRIEB,EIB_AUSSAGE_DE,"",KANTART,EIB_ARTCODE,""
    -> AttributeCreator_8
AttributeCreator_8
    ATTR_LIST = RES_ID,2,DAR_OID,GEODB.NPL_VEFE_$(BFSNR),THE_ID,1,EIB_SORT,10
    -> UUIDGenerator
Note: GEODB.NPL_NHSF
GEODB.NPL_NHSF (reader GEODATABASE_SDE_1)
    attributes: BFSNR smallint, REL_ID char(100), KANTART char(100), BESCHRIEB char(80)
    -> AttributeRenamer_8
AttributeRenamer_8
    ATTR_LIST = REL_ID,EIB_OID,""
    -> PythonCaller_3
PythonCaller_3
    PYTHONSOURCE:
      import fmeobjects

      def getAussageNHSF(feature):
          beschrieb = feature.getAttribute("BESCHRIEB")
          kantart = feature.getAttribute("KANTART")
          aussage = kantart

          if beschrieb is not None and beschrieb != "":
              aussage = kantart + " (" + beschrieb + ")"

          feature.setAttribute("EIB_AUSSAGE_DE", aussage)
    PYTHONSYMBOL = getAussageNHSF
    NEW_ATTRIBUTES = EIB_AUSSAGE_DE
    -> AttributeCreator_9
AttributeCreator_9
    ATTR_LIST = RES_ID,1,DAR_OID,GEODB.NPL_NHSF_$(BFSNR),THE_ID,1,EIB_SORT,3000
    -> UUIDGenerator
Note: GEODB.NPL_WEWRF
GEODB.NPL_WEWRF (reader GEODATABASE_SDE_1)
    attributes: BFSNR smallint, REL_ID char(100), ART char(100)
    -> AttributeRenamer_12
AttributeRenamer_12
    ATTR_LIST = REL_ID,EIB_OID,"",ART,EIB_AUSSAGE_DE,""
    -> AttributeCreator_13
AttributeCreator_13
    ATTR_LIST = RES_ID,1,DAR_OID,GEODB.NPL_WEWRF_$(BFSNR),THE_ID,1,EIB_SORT,4000
    -> UUIDGenerator
Note: GEODB.NPL_GNNUTZZO
GEODB.NPL_GNNUTZZO (reader GEODATABASE_SDE_1)
    attributes: BFSNR smallint, REL_ID char(100), ZONENABK char(12), ZONENNAME char(60), geodb_oid integer, OBJECTID integer, NAME char(31), VERBINDLKT char(100), ZONENCODE char(12), KANTZONE char(100), AZ float, AZART char(40), NZTYP char(100), BKTYP char(100), SHAPE.AREA double, SHAPE.LEN double
    -> AttributeRenamer_17
    -> AttributeRemover_4
AttributeRenamer_17
    ATTR_LIST = REL_ID,EIB_OID,"",NZTYP,EIB_AUSSAGE_DE,""
    -> AttributeCreator_18
AttributeCreator_18
    ATTR_LIST = RES_ID,1,DAR_OID,GEODB.NPL_GNNUTZZO_$(BFSNR)_NZP,GEODB.NPL_GNGU_$(BFSNR),THE_ID,1,EIB_SORT,100
    -> AttributeValueMapper_8
AttributeValueMapper_8
    DIRECTION = Forward (Source To Destination)
    VAL_ATTR = EIB_SORT
    DEFAULT_VALUE = 100
    LUT = Andere Flächen: Gewässer,122,Andere Flächen: Verkehrsanlagen,123,Andere Flächen: Wald,121,Dienstleistungszone (D),103,Freifläche A (Zone für öff. Nutzungen FA),105,Freifläche A* (Zone für priv. Bauten + Anl. im allg. Int. FA*),109,Freifläche B (Zone für öff. Nutzungen FB),106,Freifläche B* (Zone für priv. Bauten + Anl. im allg. Int. FB*),110,Freifläche C (Zone für öff. Nutzungen FC),107,Freifläche C* (Zone für priv. Bauten + Anl. im allg. Int. FC*),111,Freifläche D (Zone für öff. Nutzungen FD),108,Freifläche D* (Zone für priv. Bauten + Anl. im allg. Int. FD*),112,Gemischte Wohnzone (WG),101,Gewerbegebiete Matte, Zone mit Planungspflicht,118,Industrie- und Gewerbezone (IG),104,Kernzone (K),102,Obere Altstadt, Zone mit Planungspflicht,116,Schutzzone A (SZA) Landschafts- + Ortsbildschutzareal,113,Schutzzone B (SZB) Landschafts- + Ortsbildschutzareal,114,Schutzzone C (SZC) Naturschutzareal,115,Untere Altstadt und Wohngebiet Matte,117,Wohnzone (W),100,Landwirtschaftszone,119,Weilerzone,120
    SRC = EIB_AUSSAGE_DE
    -> AttributeRemover_6
AttributeRemover_6
    REMOVE_ATTRS = BKTYP
    -> UUIDGenerator
AttributeRemover_4
    REMOVE_ATTRS = NZTYP
    -> BulkAttributeRenamer
BulkAttributeRenamer
    REPLACE_STR = bkl_
    ATTRCHOICE = All Attributes
    PATTERN_ACTION_DISP = Add String Prefix
    -> GeometryValidator
Note: GEODB.NPL_GNBAUW
GEODB.NPL_GNBAUW (reader GEODATABASE_SDE_1)
    attributes: BFSNR smallint, REL_ID char(100), GEBLAENGE smallint, GEBTIEFE smallint, BAUWEISTYP char(100), GEBLANGUNB char(20), GEBTIEFUNB char(20)
    -> BulkAttributeRenamer_2
BulkAttributeRenamer_2
    REPLACE_STR = bw_
    ATTRCHOICE = All Attributes
    PATTERN_ACTION_DISP = Add String Prefix
    -> GeometryValidator
Note: Einige Strassenparzellen / sind nicht sauber. Damit / werden sie repariert.
GeometryValidator
    CHECK_HOLE_TOUCHING_POLYGON = Yes
    NULL_REMOVAL = NULL_REMOVAL
    TYPE_REPAIR = TYPE_REPAIR
    SELF_INTERSECTING = SELF_INTERSECTING
    PRESETS = Custom
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = Yes
    ISSUE_ATTR_NAME = _issues
    NAN_REMOVAL = NAN_REMOVAL
    PASSED -> ArcSDEGridSnapper
    REPAIRED -> ArcSDEGridSnapper
ArcSDEGridSnapper
    YMIN = -33067900
    OUTPUT_INT = No
    ZMIN = 0
    PRECISION_DISPLAY = High precision (53 bit)
    XMIN = -29386400
    ZSCALE = 1
    SCALE = 10000
    SNAPPED -> AreaOnAreaOverlayer
AreaOnAreaOverlayer
    OVC_ATTR = _overlaps
    AREA -> AreaCalculator
AreaCalculator
    AREA_ATTR = _flaeche
    AREA_TYPE = Plane Area
    MULT = 1
    -> Tester
Note: AreaOnArea produziert sehr / viele Sliver-Polygone. Sie / werden herausgefiltert.
Tester
    TEST_MODE = Automatic
    TEST_DESCRIPTION = ""
    BOOL_OP = OR
    TEST_CLAUSE = TEST @Value(_flaeche) > 0.2
    PASSED -> PythonCaller_7
    FAILED -> Logger_FAILED
Note: Aussage zusammensetzen
PythonCaller_7
    PYTHONSOURCE:
      import fmeobjects

      def getAussageBWBKL(feature):
          aussage = ""
          bauklasse = feature.getAttribute("bkl_BKTYP")
          bauweise = feature.getAttribute("bw_BAUWEISTYP")
          gebtiefe = feature.getAttribute("bw_GEBTIEFE")
          gebtiefunb = feature.getAttribute("bw_GEBTIEFUNB")
          geblaenge = feature.getAttribute("bw_GEBLAENGE")
          geblangunb = feature.getAttribute("bw_GEBLANGUNB")

          # zuerst Symbole berechnen (Entweder "", Unendlichkeit oder Zahl)
          geblangsym = ""
          if geblangunb is not None and geblangunb != "":
              geblangsym = u"\u221E"
          elif geblaenge is not None and geblaenge != "":
              geblangsym = str(geblaenge)

          gebtiefsym = ""
          if gebtiefunb is not None and gebtiefunb != "":
              gebtiefsym = u"\u221E"
          elif gebtiefe is not None and gebtiefe != "":
              gebtiefsym = str(gebtiefe)

          # Eine Bauklasse hat es immer (flächendeckend), daher keine Prüfung auf None oder leer
          if bauklasse is not None and bauklasse != "":
              aussage = bauklasse + "; "
          else:
              aussage = "Bauklasse: keine<br/>"

          if bauweise is not None and bauweise != "": # Nur wenn bauweise abgefüllt, wird der Rest ausgewertet
              aussage = aussage + "Bauweise " + bauweise
              if geblangsym == "" and gebtiefsym == "":
                  aussage = aussage + ", max. Gebaeudelaenge/-tiefe [m] = keine"
              else:
                  aussage = aussage + ", max. Gebaeudelaenge/-tiefe [m] = " + geblangsym + " / " + gebtiefsym
          else:
              aussage = aussage + "Bauweise keine"

          feature.setAttribute("EIB_AUSSAGE_DE", aussage)
    PYTHONSYMBOL = getAussageBWBKL
    NEW_ATTRIBUTES = EIB_AUSSAGE_DE
    -> UUIDGenerator_4
UUIDGenerator_4
    UUID_ATTR = EIB_OID
    -> AttributeCreator_21
AttributeCreator_21
    ATTR_LIST = RES_ID,1,DAR_OID,GEODB.NPL_GNNUTZZO_$(BFSNR)_BKL,GEODB.NPL_GNGU_$(BFSNR),GEODB.NPL_ABGRENZ_$(BFSNR),GEODB.NPL_GNBAUW_$(BFSNR),THE_ID,1,_typ,spez,EIB_SORT,200
    -> AttributeValueMapper_9
AttributeValueMapper_9
    DIRECTION = Forward (Source To Destination)
    VAL_ATTR = EIB_SORT
    DEFAULT_VALUE = 200
    LUT = Andere Flächen: Gewässer,215,Andere Flächen: Verkehrsanlagen,216,Andere Flächen: Wald,214,Bauklasse 1,200,Bauklasse 2,201,Bauklasse 3,202,Bauklasse 4,203,Bauklasse 5,204,Bauklasse 6,205,Bauklasse E, Erhaltung der best. Bebauungsstruktur,206,Festlegung der Bebauung mittels spezieller Vorschriften,207,Gewerbegebiete Matte, Zone mit Planungspflicht,211,Obere Altstadt, Zone mit Planungspflicht,209,Untere Altstadt und Wohngebiet Matte,210,Zone im öffentlichen Interesse,208,Landwirtschaftszone,212,Weilerzone,213
    SRC = bkl_BKTYP
    -> AttributeRemover_5
AttributeRemover_5
    LIST_ATTRS = _ArcSDE_Duplicate{} _issues{}.issue_found _issues{}.location_sample.x _issues{} _issues{}.location_sample.y _issues{}.location_sample.z
    REMOVE_ATTRS = bkl_BFSNR,bkl_BKTYP,bw_BFSNR,bw_GEBLAENGE,bw_GEBTIEFE,bw_BAUWEISTYP,bw_GEBLANGUNB,bw_GEBTIEFUNB,_ArcSDE_Error,_overlaps,_flaeche
    -> UUIDGenerator
Logger_FAILED
    MESSAGE = Kleinstflächen nach Union
    MAXFEATS = 20
    MAXCOORDS = 20
Note: GEODB.NPL_NHSL
GEODB.NPL_NHSL (reader GEODATABASE_SDE_1)
    attributes: BFSNR smallint, REL_ID char(100), KANTART char(100), BESCHRIEB char(80)
    -> AttributeRenamer_9
AttributeRenamer_9
    ATTR_LIST = REL_ID,EIB_OID,""
    -> PythonCaller_4
PythonCaller_4
    PYTHONSOURCE:
      import fmeobjects

      def getAussageNHSL(feature):
          beschrieb = feature.getAttribute("BESCHRIEB")
          kantart = feature.getAttribute("KANTART")
          aussage = kantart

          if beschrieb is not None and beschrieb != "":
              aussage = kantart + " (" + beschrieb + ")"

          feature.setAttribute("EIB_AUSSAGE_DE", aussage)
    PYTHONSYMBOL = getAussageNHSL
    NEW_ATTRIBUTES = EIB_AUSSAGE_DE
    -> AttributeCreator_10
AttributeCreator_10
    ATTR_LIST = RES_ID,1,DAR_OID,GEODB.NPL_NHSL_$(BFSNR),THE_ID,1,EIB_SORT,3100
    -> UUIDGenerator
Note: GEODB.NPL_NHSP
GEODB.NPL_NHSP (reader GEODATABASE_SDE_1)
    attributes: BFSNR smallint, REL_ID char(100), KANTART char(100), BESCHRIEB char(80)
    -> AttributeRenamer_10
AttributeRenamer_10
    ATTR_LIST = REL_ID,EIB_OID,""
    -> PythonCaller_5
PythonCaller_5
    PYTHONSOURCE:
      import fmeobjects

      def getAussageNHSP(feature):
          beschrieb = feature.getAttribute("BESCHRIEB")
          kantart = feature.getAttribute("KANTART")
          aussage = kantart

          if beschrieb is not None and beschrieb != "":
              aussage = kantart + " (" + beschrieb + ")"

          feature.setAttribute("EIB_AUSSAGE_DE", aussage)
    PYTHONSYMBOL = getAussageNHSP
    NEW_ATTRIBUTES = EIB_AUSSAGE_DE
    -> AttributeCreator_11
AttributeCreator_11
    ATTR_LIST = RES_ID,1,DAR_OID,GEODB.NPL_NHSP_$(BFSNR),THE_ID,1,EIB_SORT,3200
    -> UUIDGenerator
Note: GEODB.NPL_GEFF
GEODB.NPL_GEFF (reader GEODATABASE_SDE_1)
    attributes: BFSNR smallint, REL_ID char(100), STUFE char(100)
    -> AttributeRenamer_11
AttributeRenamer_11
    ATTR_LIST = REL_ID,EIB_OID,"",STUFE,EIB_AUSSAGE_DE,""
    -> AttributeCreator_12
AttributeCreator_12
    ATTR_LIST = RES_ID,1,DAR_OID,GEODB.NPL_GEFF_$(BFSNR),THE_ID,1,EIB_SORT,5000
    -> UUIDGenerator
Note: GEODB.NPL_WEWRL
GEODB.NPL_WEWRL (reader GEODATABASE_SDE_1)
    attributes: BFSNR smallint, REL_ID char(100), ART char(100)
    -> AttributeRenamer_13
AttributeRenamer_13
    ATTR_LIST = REL_ID,EIB_OID,"",ART,EIB_AUSSAGE_DE,""
    -> AttributeCreator_14
AttributeCreator_14
    ATTR_LIST = RES_ID,1,DAR_OID,GEODB.NPL_WEWRL_$(BFSNR),THE_ID,1,EIB_SORT,4100
    -> UUIDGenerator
Note: GEODB.NPL_WAABPER
GEODB.NPL_WAABPER (reader GEODATABASE_SDE_1)
    attributes: BFSNR smallint, REL_ID char(100)
    -> AttributeRenamer_14
AttributeRenamer_14
    ATTR_LIST = REL_ID,EIB_OID,""
    -> AttributeCreator_15
AttributeCreator_15
    ATTR_LIST = RES_ID,1,DAR_OID,GEODB.NPL_WAABPER_$(BFSNR),THE_ID,17,EIB_AUSSAGE_DE,Waldabstandslinie-Perimeter,EIB_SORT,100
    -> UUIDGenerator
Note: GEODB.NPL_GEGEWF
GEODB.NPL_GEGEWF (reader GEODATABASE_SDE_1)
    attributes: BFSNR smallint, REL_ID char(100), ART char(100)
    -> AttributeRenamer_15
AttributeRenamer_15
    ATTR_LIST = REL_ID,EIB_OID,"",ART,EIB_AUSSAGE_DE,""
    -> AttributeCreator_16
AttributeCreator_16
    ATTR_LIST = RES_ID,1,DAR_OID,GEODB.NPL_GEGEWF_$(BFSNR),THE_ID,1,EIB_SORT,6000
    -> UUIDGenerator
Note: GEODB.NPL_GEGEWL
GEODB.NPL_GEGEWL (reader GEODATABASE_SDE_1)
    attributes: BFSNR smallint, REL_ID char(100), ART char(100)
    -> AttributeRenamer_16
AttributeRenamer_16
    ATTR_LIST = REL_ID,EIB_OID,"",ART,EIB_AUSSAGE_DE,""
    -> AttributeCreator_17
AttributeCreator_17
    ATTR_LIST = RES_ID,1,DAR_OID,GEODB.NPL_GEGEWL_$(BFSNR),THE_ID,1,EIB_SORT,6100
    -> UUIDGenerator
Note: GEODB.NPL_UEPROJ
GEODB.NPL_UEPROJ (reader GEODATABASE_SDE_1)
    attributes: BFSNR smallint, REL_ID char(100), KANTART char(100), LINIENABK char(12), geodb_oid integer, OBJECTID integer, NAME char(31), VERBINDLKT char(100), LINIENCODE char(12), BESCHRIEB char(80), GENEHMDAT date, PLANBESCHR char(30), SHAPE.LEN double
    -> AttributeRenamer_19
AttributeRenamer_19
    ATTR_LIST = REL_ID,EIB_OID,"",LINIENABK,EIB_ARTCODE,""
    -> PythonCaller_6
PythonCaller_6
    PYTHONSOURCE:
      import fmeobjects

      def getAussageUEPROJ(feature):
          beschrieb = feature.getAttribute("BESCHRIEB")
          kantart = feature.getAttribute("KANTART")
          aussage = kantart

          if beschrieb is not None and beschrieb != "":
              aussage = beschrieb

          feature.setAttribute("EIB_AUSSAGE_DE", aussage)
    PYTHONSYMBOL = getAussageUEPROJ
    NEW_ATTRIBUTES = EIB_AUSSAGE_DE
    -> AttributeCreator_20
AttributeCreator_20
    ATTR_LIST = RES_ID,2,DAR_OID,GEODB.NPL_UEPROJ_$(BFSNR),THE_ID,1,EIB_SORT,15
    -> AttributeValueMapper_7
AttributeValueMapper_7
    DIRECTION = Forward (Source To Destination)
    VAL_ATTR = EIB_SORT
    DEFAULT_VALUE = 15
    LUT = Baulinie,15,Arkadenbaulinie,16,Baulinie für Umbauten,17,Baulinie für unterirdische Bauten,18,Baulinie mit bes. Bestimmungen,19,Erdgeschossbaulinie,20,Gestaltungsbaulinie,21,Hauptbaulinie,22,Hilfsbaulinie,23,Hofbaulinie,24,Laubenfluchtlinie,25,Parterrebaulinie,26,Sockelbaulinie,27,Strassenbaulinie,28,Vordachbaulinie,29,seitliche und rückwärtige Baulinie,30
    SRC = BESCHRIEB
    -> UUIDGenerator
Note: GEODB.NPL_GNGU / enthält nur in Bern / Eigentumsbeschränkungen
GEODB.NPL_GNGU (reader GEODATABASE_SDE_1)
    attributes: BFSNR smallint, REL_ID char(100), ZONENABK char(12), ZONENNAME char(60), geodb_oid integer, OBJECTID integer, NAME char(31), VERBINDLKT char(100), ZONENCODE char(12), KANTZONE char(100), AZART char(40), AZ float, SHAPE.AREA double, SHAPE.LEN double
    -> AttributeValueMapper_2
Note: Unterschiedliche Reihenfolge für / UEO, ZPP und Altstadperimeter
AttributeValueMapper_2
    DIRECTION = Forward (Source To Destination)
    VAL_ATTR = EIB_SORT
    LUT = 69,60,62,50,61,250
    SRC = ZONENCODE
    -> AttributeValueMapper_3
Note: Unterschiedliche Darstellung für / UEO, ZPP und Altstadtperimeter
AttributeValueMapper_3
    DIRECTION = Forward (Source To Destination)
    VAL_ATTR = DAR_OID
    LUT = 69,GEODB.NPL_GNNUTZZO_351_NZP,GEODB.NPL_GNGU_351,62,GEODB.NPL_GNNUTZZO_351_NZP,GEODB.NPL_GNGU_351,61,GEODB.NPL_GNNUTZZO_351_BKL,GEODB.NPL_GNGU_351,GEODB.NPL_ABGRENZ_351,GEODB.NPL_GNBAUW_351
    SRC = ZONENCODE
    -> AttributeRemover_11
AttributeRemover_11
    REMOVE_ATTRS = ZONENCODE
    -> AttributeRenamer_18
AttributeRenamer_18
    ATTR_LIST = ZONENABK,EIB_ARTCODE,"",ZONENNAME,EIB_AUSSAGE_DE,"",REL_ID,EIB_OID,""
    -> AttributeCreator_19
AttributeCreator_19
    ATTR_LIST = RES_ID,1,THE_ID,1
    -> UUIDGenerator
Note: FLA_OID als UUID
UUIDGenerator
    UUID_ATTR = FLA_OID
    -> TimeStamper
Note: publiziertAb (heute)
TimeStamper
    FMT = FME Date (^Y^m^d)
    TIME_ATTR = FLA_PUBLIZIERTAB
    -> AttributeRemover_3
AttributeRemover_3
    REMOVE_ATTRS = KANTART,BESCHRIEB
    -> AttributeCreator
Note: Attribute erstellen
AttributeCreator
    ATTR_LIST = EIB_AUSSAGE_FR,@Value(EIB_AUSSAGE_DE),EIB_PUBLIZIERTAB,@Value(FLA_PUBLIZIERTAB),FLA_LIEFEREINHEIT,$(LIEFEREINHEIT),EIB_LIEFEREINHEIT,$(LIEFEREINHEIT),AMT_OID,ch.be.bve.agi.$(BFSNR),LIN_OID,@Value(FLA_OID),LIN_PUBLIZIERTAB,@Value(FLA_PUBLIZIERTAB),LIN_LIEFEREINHEIT,$(LIEFEREINHEIT),PUN_OID,@Value(FLA_OID),PUN_PUBLIZIERTAB,@Value(FLA_PUBLIZIERTAB),PUN_LIEFEREINHEIT,$(LIEFEREINHEIT)
    -> AttributeRemover
    -> GeometryFilter
    -> TestFilter
GeometryFilter
    BREAK_AGG = No
    POINT -> OEREB.PUNKT (writer GEODATABASE_SDE_2)
    LINE -> OEREB.LINIE (writer GEODATABASE_SDE_2)
    AREA -> OEREB.FLAECHE (writer GEODATABASE_SDE_2)
    ARC -> OEREB.LINIE (writer GEODATABASE_SDE_2)
    NULL -> GeometryFilter_Null
Note: OEREB.FLAECHE
OEREB.FLAECHE (writer GEODATABASE_SDE_2)
    attributes: FLA_OID char(128), FLA_XTF_ID char(128), FLA_PUBLIZIERTAB date, FLA_METAGEO_DE char(1023), FLA_METAGEO_FR char(1023), FLA_LIEFEREINHEIT smallint, EIB_OID char(128), AMT_OID char(128), RES_ID integer
Note: OEREB.LINIE
OEREB.LINIE (writer GEODATABASE_SDE_2)
    attributes: LIN_OID char(128), LIN_XTF_ID char(128), LIN_PUBLIZIERTAB date, LIN_METAGEO_DE char(1023), LIN_METAGEO_FR char(1023), LIN_LIEFEREINHEIT integer, EIB_OID char(128), AMT_OID char(128), RES_ID integer
GeometryFilter_Null: Logger
    MESSAGE = NULL-Geometrie gefunden:
    MAXFEATS = 100
    MAXCOORDS = 20
Note: OEREB.PUNKT
OEREB.PUNKT (writer GEODATABASE_SDE_2)
    attributes: PUN_OID char(128), PUN_XTF_ID char(128), PUN_PUBLIZIERTAB date, PUN_METAGEO_DE char(1023), PUN_METAGEO_FR char(1023), PUN_LIEFEREINHEIT integer, EIB_OID char(128), AMT_OID char(128), RES_ID integer
TestFilter
    TEST_LIST = BOOL_OP,OR,COMPOSITE_TEST,<Unused>,TEST_CLAUSE,"TEST @Value(_typ) = spez",SPEZ
    DEFAULT_VALUE = <UNFILTERED>
    <UNFILTERED> -> AttributeRemover
    SPEZ -> AttributeRemover_7
AttributeRemover
    REMOVE_ATTRS = BFSNR,bkl_REL_ID,bw_REL_ID,_typ,FLA_OID,FLA_PUBLIZIERTAB,FLA_LIEFEREINHEIT,LIN_OID,LIN_PUBLIZIERTAB,LIN_LIEFEREINHEIT,PUN_OID,PUN_PUBLIZIERTAB,PUN_LIEFEREINHEIT
    -> Aggregator
Note: Gruppieren nach Eigentums- / beschraenkung
Aggregator
    GROUP_BY = EIB_OID EIB_ARTCODE EIB_AUSSAGE_DE RES_ID DAR_OID THE_ID EIB_SORT EIB_AUSSAGE_FR EIB_PUBLIZIERTAB EIB_LIEFEREINHEIT AMT_OID
    MODE = Assemble One Level
    ACCUM_ATTRS_NAME = No
    SEP = ,
    AGGREGATE_TYPE = Homogeneous Collection (If Possible)
    ORDERED = No
    AGGREGATE -> AttributeRemover_2
    AGGREGATE -> DuplicateRemover
DuplicateRemover
    KEYATTR = EIB_OID
    UNIQUE -> OEREB.EIGENTUMSBESCHRAENKUNG (writer ORACLE8I_DB_1)
    DUPLICATE -> Logger_DUPLICATE
    UNIQUE -> unique_eib_oid (writer FFS_1)
Note: OEREB.EIGENTUMSBESCHRAENKUNG
OEREB.EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), THE_ID number(10,0), EIB_SORT number(10,0)
AttributeRemover_2
    REMOVE_ATTRS = EIB_ARTCODE,EIB_AUSSAGE_DE,RES_ID,DAR_OID,THE_ID,EIB_SORT,EIB_AUSSAGE_FR,EIB_PUBLIZIERTAB,EIB_LIEFEREINHEIT,AMT_OID
    -> FeatureMerger [input 2]
AttributeRemover_7
    REMOVE_ATTRS = BFSNR,_typ,FLA_OID,FLA_PUBLIZIERTAB,FLA_LIEFEREINHEIT,LIN_OID,LIN_PUBLIZIERTAB,LIN_LIEFEREINHEIT,PUN_OID,PUN_PUBLIZIERTAB,PUN_LIEFEREINHEIT
    -> Aggregator_2
Note: Gruppieren nach Eigentums- / beschraenkung
Aggregator_2
    GROUP_BY = EIB_OID EIB_ARTCODE EIB_AUSSAGE_DE RES_ID DAR_OID THE_ID EIB_SORT bkl_REL_ID bw_REL_ID EIB_AUSSAGE_FR EIB_PUBLIZIERTAB EIB_LIEFEREINHEIT AMT_OID
    MODE = Assemble One Level
    ACCUM_ATTRS_NAME = No
    SEP = ,
    AGGREGATE_TYPE = Homogeneous Collection (If Possible)
    ORDERED = No
    AGGREGATE -> AttributeRemover_8
AttributeRemover_8
    REMOVE_ATTRS = EIB_ARTCODE,EIB_AUSSAGE_DE,RES_ID,DAR_OID,THE_ID,EIB_SORT,EIB_AUSSAGE_FR,EIB_PUBLIZIERTAB,EIB_LIEFEREINHEIT,AMT_OID
    -> FeatureMerger_2 [input 1]
    -> FeatureMerger_3 [input 1]
Note: GEODB.NPL_RVT
GEODB.NPL_RVT (reader GEODATABASE_SDE_1) [off]
    attributes: geodb_oid integer, OBJECTID integer, BFSNR smallint, RELID char(100), ARTIKELNR char(40), ART char(50), TEXTIMWEB char(200), TITEL char(200), OFFIZTITEL char(200), ABKUERZUNG char(10), OFFIZNR char(20), NAME char(31)
    -> UUIDGenerator_2
Note: GEODB.NPL_RVT_VORSORT / (nicht Teil des Geoprodukts; / nur hier ist die Sortierung drin)
GEODB.NPL_RVT_VORSORT (reader GEODATABASE_SDE_1)
    attributes: BFSNR smallint, NAME char(31), RELID char(100), ARTIKELNR char(40), ART char(50), TEXTIMWEB char(200), TITEL char(200), OFFIZTITEL char(200), ABKUERZUNG char(10), OFFIZNR char(20), VOR_SORT integer
    -> UUIDGenerator_2
Note: VOR_OID als UUID
UUIDGenerator_2
    UUID_ATTR = VOR_OID
    -> TimeStamper_2
Note: publiziertAb (heute)
TimeStamper_2
    FMT = FME Date (^Y^m^d)
    TIME_ATTR = VOR_PUBLIZIERTAB
    -> AttributeRenamer_2
Note: Attribute umbenennen
AttributeRenamer_2
    ATTR_LIST = ABKUERZUNG,VOR_ABKUERZUNG_DE,"",ARTIKELNR,HIV_ARTNR,"",OFFIZNR,VOR_OFFIZIELLENR,"",OFFIZTITEL,VOR_OFFIZIELLERTITEL_DE,"",TEXTIMWEB,VOR_TEXTIMWEB_DE,"",TITEL,VOR_TITEL_DE,"",RELID,EIB_OID,""
    -> AttributeCreator_2
Note: Attribute erstellen
AttributeCreator_2
    ATTR_LIST = VOR_TEXTIMWEB_FR,@Value(VOR_TEXTIMWEB_DE),VOR_TITEL_FR,@Value(VOR_TITEL_DE),VOR_OFFIZIELLERTITEL_FR,@Value(VOR_OFFIZIELLERTITEL_DE),VOR_ABKUERZUNG_FR,@Value(VOR_ABKUERZUNG_DE),RES_ID,1,AMT_OID,ch.be.bve.agi.$(BFSNR),VOR_LIEFEREINHEIT,$(LIEFEREINHEIT),HIV_LIEFEREINHEIT,$(LIEFEREINHEIT)
    -> AttributeValueMapper
Note: Dokumenttyp mappen
AttributeValueMapper
    DIRECTION = Forward (Source To Destination)
    VAL_ATTR = VOA_ID
    LUT = Rechtsvorschrift,1,Gesetzliche Grundlage,2,Hinweis,3
    SRC = ART
    -> FeatureMerger [input 1]
    -> FeatureMerger_2 [input 2]
    -> FeatureMerger_3 [input 2]
Note: Erstes Mergen für alle / Ebenen (ausser Bauklassen / und Bauweisen)
FeatureMerger
    PROCESS_DUPS = No
    MERGE_TYPE = Attributes Only
    SUPPLIERS_FIRST = No
    JOIN_KEYS = @Value(EIB_OID) @Value(EIB_OID)
    MERGED -> DuplicateRemover_2
    MERGED -> DuplicateRemover_3
Note: Zweites Mergen für / Bauklassen-RELID;
FeatureMerger_2
    PROCESS_DUPS = No
    MERGE_TYPE = Attributes Only
    SUPPLIERS_FIRST = No
    JOIN_KEYS = @Value(bkl_REL_ID) @Value(EIB_OID)
    SUPPLIER_PREFIX_DUMMY = YES
    MERGED -> DuplicateRemover_2
    DUPLICATE_SUPPLIER -> DuplicateRemover_2
    MERGED -> DuplicateRemover_3
    DUPLICATE_SUPPLIER -> DuplicateRemover_3
Note: Drittes Mergen für / Bauweise-RELID
Note: 16.01.2015: / Deaktiviert, weil es immer zu / Duplikaten der Bauordnung kommt. / Da die Bauweise immer die Bauordnung / als Rechtsvorschrift hat und die / Bauordnung aber eh schon über / die Bauklasse vorliegt, kann auf / diesen Schritt verzichtet werden. Es / sollte dann keine Duplikate mehr / geben.
FeatureMerger_3 [off]
    PROCESS_DUPS = No
    MERGE_TYPE = Attributes Only
    SUPPLIERS_FIRST = No
    JOIN_KEYS = @Value(bw_REL_ID) @Value(EIB_OID)
    SUPPLIER_PREFIX_DUMMY = YES
    DUPLICATE_SUPPLIER -> DuplicateRemover_2
    MERGED -> DuplicateRemover_2
    MERGED -> DuplicateRemover_3
    DUPLICATE_SUPPLIER -> DuplicateRemover_3
Note: Doppelte Dokumente / (gleiche ID) löschen
DuplicateRemover_2
    KEYATTR = EIB_OID VOR_OID
    UNIQUE -> UUIDGenerator_3
UUIDGenerator_3
    UUID_ATTR = HIV_ID
    -> AttributeRemover_12
AttributeRemover_12
    REMOVE_ATTRS = BFSNR,ART,VOR_TEXTIMWEB_DE,VOR_TITEL_DE,VOR_OFFIZIELLERTITEL_DE,VOR_ABKUERZUNG_DE,VOR_OFFIZIELLENR,NAME,VOR_SORT,VOR_PUBLIZIERTAB,VOR_TEXTIMWEB_FR,VOR_TITEL_FR,VOR_OFFIZIELLERTITEL_FR,VOR_ABKUERZUNG_FR,RES_ID,AMT_OID,VOR_LIEFEREINHEIT,VOA_ID,bkl_REL_ID,bw_REL_ID
    -> FeatureMerger_5 [input 1]
Note: Doppelte Dokumente / (gleiche ID) löschen
DuplicateRemover_3
    KEYATTR = VOR_OID
    UNIQUE -> AttributeRemover_9
AttributeRemover_9
    REMOVE_ATTRS = BFSNR,EIB_OID,HIV_ARTNR,ART,NAME,HIV_LIEFEREINHEIT,bkl_REL_ID,bw_REL_ID
    -> DuplicateRemover_4
Note: Alle Felder identisch / ausser VOR_OID
DuplicateRemover_4
    KEYATTR = VOR_TEXTIMWEB_DE VOR_TITEL_DE VOR_OFFIZIELLERTITEL_DE VOR_ABKUERZUNG_DE VOR_OFFIZIELLENR VOR_SORT VOR_PUBLIZIERTAB VOR_TEXTIMWEB_FR VOR_TITEL_FR VOR_OFFIZIELLERTITEL_FR VOR_ABKUERZUNG_FR RES_ID AMT_OID VOR_LIEFEREINHEIT VOA_ID
    UNIQUE -> OEREB.VORSCHRIFT (writer ORACLE8I_DB_1)
    UNIQUE -> FeatureMerger_4 [input 2]
    DUPLICATE -> AttributeRenamer_20
AttributeRenamer_20
    ATTR_LIST = VOR_OID,duplicate_VOR_OID,""
    -> FeatureMerger_4 [input 1]
Note: Die VOR_OID des Unique-Dokuments / suchen, das in die Tabelle ge- / schrieben wird. Mergen über alle / Attribute ausser VOR_OID.
FeatureMerger_4
    PROCESS_DUPS = No
    MERGE_TYPE = Attributes Only
    SUPPLIER_PREFIX = unique_
    SUPPLIERS_FIRST = No
    JOIN_KEYS = @Value(AMT_OID) @Value(AMT_OID) @Value(RES_ID) @Value(RES_ID) @Value(VOA_ID) @Value(VOA_ID) @Value(VOR_ABKUERZUNG_DE) @Value(VOR_ABKUERZUNG_DE) @Value(VOR_ABKUERZUNG_FR) @Value(VOR_ABKUERZUNG_FR) @Value(VOR_LIEFEREINHEIT) @Value(VOR_LIEFEREINHEIT) @Value(VOR_OFFIZIELLENR) @Value(VOR_OFFIZIELLENR) @Value(VOR_OFFIZIELLERTITEL_DE) @Value(VOR_OFFIZIELLERTITEL_DE) @Value(VOR_OFFIZIELLERTITEL_DE) @Value(VOR_OFFIZIELLERTITEL_FR) @Value(VOR_PUBLIZIERTAB) @Value(VOR_PUBLIZIERTAB) @Value(VOR_TEXTIMWEB_DE) @Value(VOR_TEXTIMWEB_DE) @Value(VOR_TEXTIMWEB_FR) @Value(VOR_TEXTIMWEB_FR) @Value(VOR_TITEL_DE) @Value(VOR_TITEL_DE) @Value(VOR_TITEL_FR) @Value(VOR_TITEL_FR) @Value(VOR_SORT) @Value(VOR_SORT)
    SUPPLIER_PREFIX_DUMMY = YES
    MERGED -> AttributeRemover_10
    NOT_MERGED -> Logger_NOT_MERGED
AttributeRemover_10
    REMOVE_ATTRS = VOR_TEXTIMWEB_DE,VOR_TITEL_DE,VOR_OFFIZIELLERTITEL_DE,VOR_ABKUERZUNG_DE,VOR_OFFIZIELLENR,VOR_SORT,VOR_PUBLIZIERTAB,VOR_TEXTIMWEB_FR,VOR_TITEL_FR,VOR_OFFIZIELLERTITEL_FR,VOR_ABKUERZUNG_FR,RES_ID,AMT_OID,VOR_LIEFEREINHEIT,VOA_ID,unique_VOR_TEXTIMWEB_DE,unique_VOR_TITEL_DE,unique_VOR_OFFIZIELLERTITEL_DE,unique_VOR_ABKUERZUNG_DE,unique_VOR_OFFIZIELLENR,unique_VOR_SORT,unique_VOR_PUBLIZIERTAB,unique_VOR_TEXTIMWEB_FR,unique_VOR_TITEL_FR,unique_VOR_OFFIZIELLERTITEL_FR,unique_VOR_ABKUERZUNG_FR,unique_RES_ID,unique_AMT_OID,unique_VOR_LIEFEREINHEIT,unique_VOA_ID
    -> FeatureMerger_5 [input 2]
Note: Bei allen HINVORs die auf eine / doppelte VOR_OID verweisen / muss die neue VOR_OID ein- / gebaut werden.
FeatureMerger_5
    PROCESS_DUPS = No
    MERGE_TYPE = Attributes Only
    SUPPLIERS_FIRST = No
    JOIN_KEYS = @Value(VOR_OID) @Value(duplicate_VOR_OID)
    SUPPLIER_PREFIX_DUMMY = YES
    MERGED -> AttributeCreator_22
    NOT_MERGED -> DuplicateRemover_5
Note: VOR_OID wird durch die / eindeutige ersetzt.
AttributeCreator_22
    ATTR_LIST = VOR_OID,@Value(unique_VOR_OID)
    -> DuplicateRemover_5
DuplicateRemover_5
    KEYATTR = EIB_OID HIV_ARTNR VOR_OID HIV_LIEFEREINHEIT
    UNIQUE -> OEREB.HINVOR (writer ORACLE8I_DB_1)
    DUPLICATE -> Logger_DUPLICATE_2
Logger_DUPLICATE_2
    MESSAGE = Doppelte Hinvor:
    MAXFEATS = 20
    MAXCOORDS = 20
Note: OEREB.HINVOR
OEREB.HINVOR (writer ORACLE8I_DB_1)
    attributes: HIV_ID nvarchar(128), HIV_XTF_ID nvarchar(128), HIV_ARTNR nvarchar(255), HIV_LIEFEREINHEIT number(5,0), EIB_OID nvarchar(128), VOR_OID nvarchar(128)
Logger_NOT_MERGED
    MESSAGE = gelöschtes DuplicateVOR:
    MAXFEATS = 20
    MAXCOORDS = 20
Note: OEREB.VORSCHRIFT
OEREB.VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)

Bookmark: Debug-Output
unique_eib_oid (writer FFS_1)
    attributes: EIB_OID char(200), EIB_ARTCODE char(200), EIB_AUSSAGE_DE char(200), RES_ID char(200), DAR_OID char(200), THE_ID char(200), EIB_AUSSAGE_FR char(200), EIB_PUBLIZIERTAB char(200), EIB_LIEFEREINHEIT char(200), AMT_OID char(200)
Logger_DUPLICATE [off]
    MESSAGE = "Doppelte EIB_OID: "
    MAXFEATS = 200
    MAXCOORDS = 20
    LOGGED -> double_eib_oid (writer FFS_1)
double_eib_oid (writer FFS_1)
    attributes: EIB_OID char(200), EIB_ARTCODE char(200), EIB_AUSSAGE_DE char(200), RES_ID char(200), DAR_OID char(200), THE_ID char(200), EIB_AUSSAGE_FR char(200), EIB_PUBLIZIERTAB char(200), EIB_LIEFEREINHEIT char(200), AMT_OID char(200)
