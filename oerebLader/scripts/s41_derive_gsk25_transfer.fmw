FME workspace s41_derive_gsk25_transfer.fmw

Parameters:
- GEODB_USERNAME =   # Geodb-Username
- GEODB_PASSWORD =   # Geodb-Passwort
- GEODB_DATABASE =   # Geodb-Database
- OEREB_DATABASE =   # Oereb-Database
- OEREB_USERNAME =   # Oereb-Username
- OEREB_PASSWORD =   # Oereb-Passwort
- LOGFILE =   # Logfile
- LIEFEREINHEIT =   # Liefereinheit
- AMT = ch.be.bve.awa   # Amt
- RECHTSSTATUS = 1   # Rechtsstatus
- THEMA_ZONEN = 13   # Thema-GSZonen
- DARST_ZONEN = GEODB.GSK25_GSK_Zone   # Darstellungsdienst Zonen
- DARST_AREALE = GEODB.GSK25_GSK_Areal   # Darstellungsdienst-Areale

Readers:
- GEODATABASE_SDE_1: GEODATABASE_SDE from sde

Writers:
- GEODATABASE_SDE_2: GEODATABASE_SDE to sde
- ORACLE8I_DB_1: ORACLE8I_DB to $(OEREB_DATABASE)

Note: GEODB.GSK25_GSK
GEODB.GSK25_GSK (reader GEODATABASE_SDE_1)
    attributes: geodb_oid integer, OBJECTID integer, GSZ_NR integer, TYP char(3), GSZ_NAME char(255), BESCHLUSS date, BESCHL_DOC char(100), REGLEM_DOC char(100), SHAPE.AREA double, SHAPE.LEN double
    -> AttributeFilter
AttributeFilter
    ATTR_NAME = TYP
    ATTR_VALUES = <EMPTY>,<MISSING>,<NULL>,<UNFILTERED>,S1,S2,S3,SA1,SA2,SA3
    S1 -> AttributeCreator_3
    S2 -> AttributeCreator_3
    S3 -> AttributeCreator_3
    SA1 -> AttributeCreator_2
    SA2 -> AttributeCreator_2
    SA3 -> AttributeCreator_2
Note: Zonen-Attribute
AttributeCreator_3
    ATTR_LIST = THE_ID,$(THEMA_ZONEN),DAR_OID,$(DARST_ZONEN),EIB_AUSSAGE_DE,Schutzzone @Value(TYP) (@Value(GSZ_NAME)),EIB_AUSSAGE_FR,Zone de protection @Value(TYP) (@Value(GSZ_NAME))
    -> AttributeRemover
Note: Areal-Attribute
AttributeCreator_2
    ATTR_LIST = THE_ID,1132,DAR_OID,$(DARST_AREALE),EIB_AUSSAGE_DE,Schutzareal @Value(TYP) (@Value(GSZ_NAME)),EIB_AUSSAGE_FR,Périmètre de protection @Value(TYP)(@Value(GSZ_NAME))
    -> AttributeRemover
AttributeRemover
    REMOVE_ATTRS = geodb_oid,OBJECTID,SHAPE.AREA,SHAPE.LEN
    -> FeatureMerger [input 1]
Note: GEODB.GSK25_GSKT
GEODB.GSK25_GSKT (reader GEODATABASE_SDE_1)
    attributes: geodb_oid integer, OBJECTID integer, TYP char(3), BEZEICH_DE char(100), BEZEICH_FR char(100)
    -> AttributeRemover_2
AttributeRemover_2
    REMOVE_ATTRS = geodb_oid,OBJECTID
    -> FeatureMerger [input 2]
FeatureMerger
    PROCESS_DUPS = No
    MERGE_TYPE = Attributes Only
    SUPPLIERS_FIRST = No
    JOIN_KEYS = @Value(TYP) @Value(TYP) AUTO
    SUPPLIER_PREFIX_DUMMY = YES
    MERGED -> UUIDGenerator
Note: FLA_OID
UUIDGenerator
    UUID_ATTR = FLA_OID
    -> UUIDGenerator_2
Note: EIB_OID
UUIDGenerator_2
    UUID_ATTR = EIB_OID
    -> UUIDGenerator_3
Note: VOR_OID
UUIDGenerator_3
    UUID_ATTR = VOR_OID
    -> AttributeRenamer
AttributeRenamer
    ATTR_LIST = TYP,EIB_ARTCODE,""
    -> DateFormatter
DateFormatter
    DATE_ATTR = BESCHLUSS
    FMT = %d.%m.%y
    SRCFMT = Unknown - Automatic Detection
    INVALID_DATE_VALUE = _FME_NO_OP_
    -> AttributeCreator
AttributeCreator
    ATTR_LIST = FLA_PUBLIZIERTAB,@Value(BESCHLUSS),EIB_PUBLIZIERTAB,@Value(BESCHLUSS),VOR_PUBLIZIERTAB,@Value(BESCHLUSS)
    -> OEREB.FLAECHE (writer GEODATABASE_SDE_2)
    -> AttributeCreator_Output
    -> OEREB.EIGENTUMSBESCHRAENKUNG (writer ORACLE8I_DB_1)
    -> UUIDGenerator_4
    -> PythonCaller
Note: OEREB.FLAECHE
OEREB.FLAECHE (writer GEODATABASE_SDE_2)
    attributes: FLA_OID char(128), FLA_XTF_ID char(128), FLA_PUBLIZIERTAB date, FLA_METAGEO_DE char(1023), FLA_METAGEO_FR char(1023), FLA_LIEFEREINHEIT integer, EIB_OID char(128), AMT_OID char(128), RES_ID integer
AttributeCreator_Output: Inspector
Note: OEREB.EIGENTUMSBESCHRAENKUNG
OEREB.EIGENTUMSBESCHRAENKUNG (writer ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), THE_ID number(10,0), EIB_SORT number(10,0)
UUIDGenerator_4
    UUID_ATTR = HIV_ID
    -> OEREB.HINVOR (writer ORACLE8I_DB_1)
Note: OEREB.HINVOR
OEREB.HINVOR (writer ORACLE8I_DB_1)
    attributes: HIV_ID nvarchar(128), HIV_XTF_ID nvarchar(128), HIV_ARTNR nvarchar(255), HIV_LIEFEREINHEIT number(6,0), EIB_OID nvarchar(128), VOR_OID nvarchar(128)
Note: Titel bilden
PythonCaller
    PYTHONSOURCE:
      import fmeobjects
      # Template Function interface:
      def processFeature(feature):
          reglement = feature.getAttribute("REGLEM_DOC").lower()

          title_de = "Reglement"
          title_fr = "Règlement"

          if "veraltet" in reglement:
              titel_de = "Rechtsvorschriften veraltet"
              titel_fr = "Prescriptions légales obsolètes"

          feature.setAttribute("VOR_TITEL_DE", titel_de)
          feature.setAttribute("VOR_TITEL_FR", titel_fr)
          feature.setAttribute("VOR_OFFIZIELLERTITEL_DE", titel_de)
          feature.setAttribute("VOR_OFFIZIELLERTITEL_FR", titel_fr)
    PYTHONSYMBOL = FeatureProcessor
    NEW_ATTRIBUTES = VOR_OFFIZIELLERTITEL_DE VOR_OFFIZIELLERTITEL_FR VOR_TITEL_DE VOR_TITEL_FR
    -> AttributeRemover_3
    -> AttributeCreator_5
AttributeRemover_3
    REMOVE_ATTRS = GSZ_NR,EIB_ARTCODE,GSZ_NAME,BESCHLUSS,BESCHL_DOC,REGLEM_DOC,EIB_LIEFEREINHEIT,FLA_LIEFEREINHEIT,VOR_LIEFEREINHEIT,HIV_LIEFEREINHEIT,THE_ID,DAR_OID,EIB_AUSSAGE_DE,EIB_AUSSAGE_FR,BEZEICH_DE,BEZEICH_FR,FLA_OID,EIB_OID,FLA_PUBLIZIERTAB,EIB_PUBLIZIERTAB,VOR_PUBLIZIERTAB,VOR_OFFIZIELLERTITEL_DE,VOR_OFFIZIELLERTITEL_FR,VOR_TITEL_DE,VOR_TITEL_FR
    -> AttributeRenamer_2
AttributeRenamer_2
    ATTR_LIST = VOR_OID,VOR_OIDURSPRUNG,""
    -> AttributeCreator_4
    -> AttributeCreator_8
Note: Gesetz hinzufügen
AttributeCreator_4
    ATTR_LIST = VOR_OIDHINWEIS,ch.admin.bk.sr.814.20
    -> UUIDGenerator_5
Note: Verordnung hinzufügen
AttributeCreator_8
    ATTR_LIST = VOR_OIDHINWEIS,ch.admin.bk.sr.814.201
    -> UUIDGenerator_5
Note: HWD_ID
UUIDGenerator_5
    UUID_ATTR = HWD_ID
    -> OEREB.HINWEIDOK (writer ORACLE8I_DB_1)
OEREB.HINWEIDOK (writer ORACLE8I_DB_1)
    attributes: HWD_ID nvarchar(128), HWD_XTF_ID nvarchar(128), HWD_LIEFEREINHEIT number(6,0), HWD_ARTNR nvarchar(255), VOR_OIDURSPRUNG nvarchar(128), VOR_OIDHINWEIS nvarchar(128)
AttributeCreator_5
    ATTR_LIST = VOR_TEXTIMWEB_DE,@Value(REGLEM_DOC),VOR_TEXTIMWEB_FR,@Value(REGLEM_DOC)
    -> OEREB.VORSCHRIFT (writer ORACLE8I_DB_1)
OEREB.VORSCHRIFT (writer ORACLE8I_DB_1)
    attributes: VOR_OID nvarchar(128), VOR_XTF_ID nvarchar(128), VOR_TEXTIMWEB_DE nvarchar(1023), VOR_TEXTIMWEB_FR nvarchar(1023), VOR_PUBLIZIERTAB date, VOR_TITEL_DE nvarchar(200), VOR_TITEL_FR nvarchar(200), VOR_OFFIZIELLERTITEL_DE nvarchar(255), VOR_OFFIZIELLERTITEL_FR nvarchar(255), VOR_ABKUERZUNG_DE nvarchar(255), VOR_ABKUERZUNG_FR nvarchar(255), VOR_OFFIZIELLENR nvarchar(20), VOR_KANTON nvarchar(2), VOR_LIEFEREINHEIT number(6,0), RES_ID number(10,0), BFS_NR number(5,0), VOA_ID number(10,0), AMT_OID nvarchar(128), DOKUMENT blob, VOR_SORT number(10,0)
