FME workspace s51_derive_darstellung.fmw

Parameters:
- OEREB2_DATABASE =   # OEREB2-Database
- OEREB2_USERNAME =   # OEREB2-Username
- OEREB2_PASSWORD =   # OEREB2-Passwort
- LIEFEREINHEIT =   # Liefereinheit
- NPL_WMS_BASE =   # WMS-Basis-URL
- OUTPUT_RV_URL =   # Output-URL Rechtsvorschriften
- LOGFILE =   # Logfile
- BFSNR =   # BFS-Nummer

Writers:
- ORACLE8I_DB_1: ORACLE8I_DB to $(OEREB2_DATABASE)

SQLCreator
    DATASET = $(OEREB2_DATABASE)
    EXPOSED_ATTRIBUTE_LIST = DAR_OID
    FORMAT = ORACLE_NONSPATIAL
    ORACLE_NONSPATIAL_PASSWORD = $(OEREB2_PASSWORD)
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USER_NAME = $(OEREB2_USERNAME)
    ORACLE_NONSPATIAL_USE_UNIFIED_DATE_ATTRS = YES
    SQL_STATEMENT = select distinct dar_oid from eigentumsbeschraenkung where eib_liefereinheit=$(LIEFEREINHEIT)
    RESULT -> PythonCaller_2
PythonCaller_2
    NEW_ATTRIBUTES = DAR_VERWEISWMS_DE DAR_VERWEISWMS_FR
    PYTHONSOURCE:
      import fme
      import fmeobjects

      def processFeature(feature):
          dar_oid = feature.getAttribute("DAR_OID")
          layername = ""

          if dar_oid.endswith(".11"):
              layername = "geodb.nupla_gngruzo"
          elif dar_oid.endswith(".12"):
              layername = "geodb.nupla_uefl_1"
          elif dar_oid.endswith(".13"):
              layername = "geodb.nupla_uefl_2"
          elif dar_oid.endswith(".14"):
              layername = "geodb.nupla_ueln"
          elif dar_oid.endswith(".15"):
              layername = "geodb.nupla_uept"
          elif dar_oid.endswith(".150"):
              layername = "geodb.nupla_uelarmes"
          elif dar_oid.endswith(".170"):
              layername = "geodb.nupla_uewaabl"

          wms = FME_MacroValues['NPL_WMS_BASE'] + layername
          feature.setAttribute("DAR_VERWEISWMS_DE", wms)
          feature.setAttribute("DAR_VERWEISWMS_FR", wms)
    PYTHONSYMBOL = processFeature
    -> StringConcatenator_6
Note: DAR_LEGENDEIMWEB_DE
StringConcatenator_6
    PARM_LINE = $(OUTPUT_RV_URL)legenden/$(BFSNR)_legende_npl_de.html
    VAL_ATTR = DAR_LEGENDEIMWEB_DE
    -> StringConcatenator_7
Note: DAR_LEGENDEIMWEB_FR
StringConcatenator_7
    PARM_LINE = $(OUTPUT_RV_URL)legenden/$(BFSNR)_legende_npl_fr.html
    VAL_ATTR = DAR_LEGENDEIMWEB_FR
    -> AttributeCreator
Note: DAR_LIEFEREINHEIT
AttributeCreator
    ATTR_LIST = DAR_LIEFEREINHEIT,$(LIEFEREINHEIT)
    -> AttributeRemover_4
AttributeRemover_4
    REMOVE_ATTRS = STH_ID,LAYERNAME_BFS
    -> DARSTELLUNGSDIENST (writer ORACLE8I_DB_1)
Note: OEREB2.DARSTELLUNGSDIENST
DARSTELLUNGSDIENST (writer ORACLE8I_DB_1)
    attributes: DAR_OID nvarchar(128), DAR_XTF_ID nvarchar(128), DAR_VERWEISWMS_DE nvarchar(1023), DAR_VERWEISWMS_FR nvarchar(1023), DAR_LEGENDEIMWEB_DE nvarchar(1023), DAR_LEGENDEIMWEB_FR nvarchar(1023), DAR_LIEFEREINHEIT number(6,0)
