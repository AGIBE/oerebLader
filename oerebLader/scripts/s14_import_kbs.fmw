FME workspace s14_import_kbs.fmw

Parameters:
- GEODB_PG_DATABASE =
- GEODB_PG_USERNAME =
- GEODB_PG_PASSWORD =
- GEODB_PG_HOST =
- GEODB_PG_PORT =
- LOGFILE =
- GEODB_WORK =
- TABELLEN =
- DATEFIELDS =   # " " Selected Attributes
- SCHEMA_NAME =   # Schema-Name

Readers:
- GEODATABASE_SDE_1: GEODATABASE_SDE in EPSG:2056

Writers:
- POSTGIS_1: POSTGIS to $(GEODB_PG_DATABASE)
- POSTGRES_1: POSTGRES to $(GEODB_PG_DATABASE)

BALISKBS_KBS (reader GEODATABASE_SDE_1)
    attributes: OBJECTID integer, STA_NR char(8), BEDEUT char(3), ART_NR smallint, ART_BEZ char(50), STA_NAME char(50), KOORD_X integer, KOORD_Y integer, HGDE_NR smallint, HGDE_NAME char(25), GEMEINDEN char(50), UNTERSUCHT char(5), STATUS_NR smallint, STATUS_BEZ char(50), PRIORI_NR smallint, PRIORI_BEZ char(50), BEW32USG smallint, STOFFE char(100), FLAECHE double, VOLUMEN char(16), ZEIT_START char(10), ZEIT_ENDE char(10), UNFALLZEIT char(10), INFOKBS char(10), EINTRAGKBS char(10), INFO char(50), SHAPE.AREA double, SHAPE.LEN double
    -> MeasureRemover
Note: M-Values werden entfernt (Routen)
MeasureRemover
    REMOVE_ALL = Yes
    -> NullAttributeMapper
Note: Leere Datumsfelder abfangen
NullAttributeMapper
    ATTRCHOICE = Selected Attributes
    ATTRLIST = $(DATEFIELDS)
    NULL_TREATMENT = Null
    OTHER_VALUE = 000000
    SOURCE_ATTR_VAL = Null
    -> PythonCaller
Note: Tabellenname erstellen
PythonCaller
    NEW_ATTRIBUTES = pg_tblname
    PYTHONSOURCE:
      import fme
      import fmeobjects

      def processFeature(feature):
          tblname_work = feature.getAttribute("fme_feature_type")
          tblname_work = tblname_work.lower()

          pg_tblname = tblname_work

          if "." in tblname_work:
              pg_tblname = tblname_work.split(".")[1]

          feature.setAttribute('pg_tblname', pg_tblname)
    PYTHONSYMBOL = processFeature
    -> Tester
Note: Enthält Feature keine Geometrie?
Tester
    BOOL_OP = OR
    TEST_CLAUSE = TEST @Value(geodb_type) = geodb_table
    PASSED -> Table1 (writer POSTGRES_1)
    FAILED -> Table1 (writer POSTGIS_1)
Note: PostgreSQL
Table1 (writer POSTGRES_1)
Note: PostGIS
Table1 (writer POSTGIS_1)
