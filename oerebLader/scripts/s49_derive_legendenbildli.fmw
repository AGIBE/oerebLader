FME workspace s49_derive_legendenbildli.fmw

Parameters:
- MAPSERVICE_BASE_URL =   # Mapservice-Basis-URL
- OEREB2_DATABASE =   # ÖREB2-DB
- OEREB2_USERNAME =   # ÖREB-Username
- OEREB2_PASSWORD =   # ÖREB2-Passwort
- LIEFEREINHEIT =   # Liefereinheit
- BFSNR =   # BFS-Nummer
- GEODB_DATABASE =   # GeoDB-Database
- GEODB_USERNAME =   # GeoDB-Username
- GEODB_PASSWORD =   # GeoDB-Passwort
- GDBV_DATABASE =   # GeoDBProzess-DB
- GDBV_USERNAME =   # GeoDBProzess-Username
- GDBV_PASSWORD =   # GeoDBProzess-Passwort
- LEGEND_BASEDIR =   # Legenden-Directory
- LEGEND_BASEURL =   # Legenden-BasisURL
- MAPSERVICE_NAME =   # Mapservice-Name
- MAPSERVICE_LEGEND_URL =   # Mapservice-Legenden-URL
- LOGFILE =   # Logfile
- TOKEN =   # Token

Readers:
- ORACLE8I_DB_1: ORACLE8I_DB from $(OEREB2_DATABASE)
- ORACLE8I_DB_2: ORACLE8I_DB from $(GEODB_DATABASE)

Writers:
- ORACLE8I_DB_3: ORACLE8I_DB to $(OEREB2_DATABASE)

Creator
    GEOMTYPE = Geometry Object
    NUM = 1
    CREATED -> HTTPFetcher
HTTPFetcher
    SAVE_FILE = No
    TARGET_ATTR_ENCODING = utf-8
    RESPONSE_HEADER_LIST_ATTR = _headers
    USE_COOKIES = No
    TARGET_URL = $(MAPSERVICE_LEGEND_URL)
    FOLLOW_REDIRECTS = Yes
    STATUS_CODE_ATTR = _http_status_code
    TARGET_ATTR = json
    AUTH_METHOD = Basic
    PROXY_AUTH_METHOD = Basic
    VERIFY_SSL_CERTIFICATES = Yes
    ERROR_ATTR = _error
    -> AttributeRemover
AttributeRemover
    LIST_ATTRS = _headers{}.value _headers{}.name _headers{}
    REMOVE_ATTRS = _creation_instance,_error,_http_status_code
    -> JSONFragmenter
JSONFragmenter
    JSON_QUERY = json["layers"][*]
    EXPLODE_FORMAT = JSON
    EXTRACT_ATTR = No
    JSON_ATTR = json
    EXPLODED -> JSONFlattener
JSONFlattener
    RECURSIVE = No
    JSON_ATTR = json
    NEW_ATTRIBUTES = layerId layerName minScale maxScale legend
    -> JSONFragmenter_2
JSONFragmenter_2
    JSON_QUERY = json[*]
    EXPLODE_FORMAT = JSON
    EXTRACT_ATTR = No
    JSON_ATTR = legend
    EXPLODED -> JSONFlattener_2
JSONFlattener_2
    RECURSIVE = Yes
    JSON_ATTR = legend
    NEW_ATTRIBUTES = label url imageData contentType
    -> StringConcatenator
StringConcatenator
    PARM_LINE = $(MAPSERVICE_BASE_URL)$(MAPSERVICE_NAME)/MapServer/@Value(layerId)/images/@Value(url)
    VAL_ATTR = image_url
    -> AttributeRemover_2
AttributeRemover_2
    REMOVE_ATTRS = json,json_type,json_index,legend
    -> AttributeRemover_5
AttributeRemover_5
    REMOVE_ATTRS = layerId,minScale,maxScale,url,imageData,contentType
    -> BulkAttributeRenamer
BulkAttributeRenamer
    CASE_CHANGE_TYPE = UPPERCASE
    ATTRCHOICE = All Attributes
    PATTERN_ACTION_DISP = Change Case
    -> BulkAttributeRenamer_2
BulkAttributeRenamer_2
    ATTRCHOICE = All Attributes
    PATTERN_ACTION_DISP = Add String Prefix
    REPLACE_STR = REST_
    -> FeatureMerger_3 [SUPPLIER]
OEREB2.EIGENTUMSBESCHRAENKUNG (reader ORACLE8I_DB_1)
    attributes: EIB_OID nvarchar(128), EIB_XTF_ID nvarchar(128), EIB_AUSSAGE_DE nclob, EIB_AUSSAGE_FR nclob, EIB_ARTCODE nvarchar(40), EIB_ARTCODELISTE nvarchar(1023), EIB_PUBLIZIERTAB date, EIB_LIEFEREINHEIT number(6,0), AMT_OID nvarchar(128), DAR_OID nvarchar(128), RES_ID number(10,0), EIB_SORT number(10,0), STH_ID number(10,0), EIB_LEGENDESYMBOL_DE nvarchar(1023), EIB_LEGENDESYMBOL_FR nvarchar(1023)
    -> Joiner
Note: DAR_VERWEISWMS_DE holen
Joiner
    ADDED_FIELDS = DAR_VERWEISWMS_DE
    TABLE = OEREB2.DARSTELLUNGSDIENST
    ORACLE8I_DB_PERSISTENT_CONNECTION = YES
    ORACLE8I_DB_SHOW_SYSTEM_TABLES = NO
    PREFETCH_EXHAUSTIVE = Yes
    JOIN_KEYS = DAR_OID DAR_OID
    FORMAT = ORACLE8I_DB
    MATCH_RULE_DISPLAY = Must Match Exactly One (1:1)
    CACHE_SIZE = 5000
    ORACLE8I_DB_SERVER_TYPE = ORACLE8i
    ORACLE8I_DB_USER_NAME = $(OEREB2_USERNAME)
    DATASET = $(OEREB2_DATABASE)
    ORACLE8I_DB_PASSWORD = $(OEREB2_PASSWORD)
    ORACLE8I_DB_REMOVE_SCHEMA_QUALIFIER = NO
    JOINED -> AttributeRemover_3
AttributeRemover_3
    REMOVE_ATTRS = EIB_XTF_ID,EIB_AUSSAGE_FR,EIB_ARTCODE,EIB_ARTCODELISTE,EIB_PUBLIZIERTAB,EIB_LIEFEREINHEIT,AMT_OID,DAR_OID,RES_ID,EIB_SORT,fme_feature_type,STH_ID,EIB_LEGENDESYMBOL_DE,EIB_LEGENDESYMBOL_FR,_matched_records,THE_ID
    -> BulkAttributeRenamer_3
BulkAttributeRenamer_3
    ATTRCHOICE = All Attributes
    PATTERN_ACTION_DISP = Add String Prefix
    REPLACE_STR = TS_
    -> FeatureMerger [REQUESTOR]
Note: Transferstruktur und Geoprodukt / abgleichen.
FeatureMerger
    MERGE_TYPE = Attributes Only
    IGNORE_NULLS = Yes
    SUPPLIERS_FIRST = No
    JOIN_KEYS = @Value(TS_EIB_OID) @Value(GPR_REL_ID) STRING
    PROCESS_DUPS = No
    SUPPLIER_PREFIX_DUMMY = YES
    MERGED -> PythonCaller_2
    NOT_MERGED -> Terminator
Note: WMS-URL parsen, Layername / ermitteln
PythonCaller_2
    PYTHONSYMBOL = processFeature
    PYTHONSOURCE:
      import fmeobjects
      import urlparse

      def processFeature(feature):
          url = feature.getAttribute("TS_DAR_VERWEISWMS_DE")
          gpr_ebene = feature.getAttribute("GPR_EBENE")

          parsed_url = urlparse.urlparse(url)
          qs = parsed_url[4]
          parsed_qs = urlparse.parse_qs(qs)

          wms_layers = parsed_qs['LAYERS'][0].split(",")

          matched_wms_layer = ""

          for wms_layer in wms_layers:
              if gpr_ebene in wms_layer:
                  matched_wms_layer = wms_layer

          feature.setAttribute("TS_WMS_LAYER", matched_wms_layer)
    NEW_ATTRIBUTES = TS_WMS_LAYER
    -> AttributeRemover_8
AttributeRemover_8
    REMOVE_ATTRS = TS_DAR_VERWEISWMS_DE
    -> FeatureMerger_2 [REQUESTOR]
Terminator
    MESSAGE = EIB_OID ohne Treffer im Geoprodukt!!!
SQLCreator
    ORACLE8I_DB_SHOW_SYSTEM_TABLES = NO
    ORACLE8I_DB_PASSWORD = $(GDBV_PASSWORD)
    EXPOSED_ATTRIBUTE_LIST = LAYER,OBJEKT,OBJEKT_FULL,OBJEKT_IDENT,SYMB_TYP
    ORACLE8I_DB_SERVER_TYPE = ORACLE8i
    FORMAT = ORACLE8I_DB
    SQL_STATEMENT = select distinct sym.objekt_ident, sym.objekt, sym.objekt_full, mxd.ebene as layer, symb_attr_orig symb_typ from gdbp.info_symb sym left join gdbp.info_mxd mxd on sym.OBJEKT_IDENT=mxd.OBJEKT_IDENT where mxd.mxd like '%$(MAPSERVICE_NAME)%'
    ORACLE8I_DB_PERSISTENT_CONNECTION = YES
    ORACLE8I_DB_USER_NAME = $(GDBV_USERNAME)
    ORACLE8I_DB_REMOVE_SCHEMA_QUALIFIER = NO
    DATASET = $(GDBV_DATABASE)
    RESULT -> BulkAttributeRenamer_5
BulkAttributeRenamer_5
    ATTRCHOICE = All Attributes
    PATTERN_ACTION_DISP = Add String Prefix
    REPLACE_STR = INFO_
    -> StringReplacer
StringReplacer
    CASE = no
    REPLACE_TEXT = " || ', ///' || "
    REGEXP = no
    SRC_ATTRS = INFO_SYMB_TYP
    NO_MATCH = _FME_NO_OP_
    FIND_TEXT = /
    -> AttributeRemover_6
AttributeRemover_6
    REMOVE_ATTRS = INFO_OBJEKT,INFO_OBJEKT_FULL,INFO_OBJEKT_IDENT
    -> FeatureMerger_2 [SUPPLIER]
FeatureMerger_2
    MERGE_TYPE = Attributes Only
    IGNORE_NULLS = Yes
    SUPPLIERS_FIRST = No
    JOIN_KEYS = @Value(TS_WMS_LAYER) @Value(INFO_LAYER) AUTO
    PROCESS_DUPS = No
    SUPPLIER_PREFIX_DUMMY = YES
    MERGED -> SQLExecutor [INITIATOR]
    NOT_MERGED -> Logger
SQLExecutor
    COMBINE_ATTRS = Keep Initiator Attributes if Conflict
    ORACLE8I_DB_SHOW_SYSTEM_TABLES = NO
    ORACLE8I_DB_PASSWORD = $(GEODB_PASSWORD)
    EXPOSED_ATTRIBUTE_LIST = VALUE
    COMBINE_GEOM = Initiator Geometry Only
    ORACLE8I_DB_SERVER_TYPE = ORACLE8i
    FORMAT = ORACLE8I_DB
    SQL_STATEMENT = SELECT DISTINCT @Value(INFO_SYMB_TYP) AS VALUE FROM @Value(GPR_EBENE) WHERE REL_ID='@Value(TS_EIB_OID)'
    ORACLE8I_DB_PERSISTENT_CONNECTION = YES
    ORACLE8I_DB_USER_NAME = $(GEODB_USERNAME)
    ORACLE8I_DB_REMOVE_SCHEMA_QUALIFIER = NO
    DATASET = $(GEODB_DATABASE)
    RESULT -> PythonCaller
PythonCaller
    PYTHONSYMBOL = processFeature
    PYTHONSOURCE:
      import fmeobjects

      def processFeature(feature):
          value = feature.getAttribute('VALUE')

          if value.endswith("///"):
              value = value.replace("///", "<Null>")
          else:
              value = value.replace("///", "")

          feature.setAttribute('VALUE', value)
    -> FeatureMerger_3 [REQUESTOR]
FeatureMerger_3
    MERGE_TYPE = Attributes Only
    IGNORE_NULLS = Yes
    SUPPLIERS_FIRST = No
    JOIN_KEYS = @Value(VALUE) @Value(REST_LABEL) AUTO @Value(INFO_LAYER) @Value(REST_LAYERNAME) AUTO
    PROCESS_DUPS = No
    SUPPLIER_PREFIX_DUMMY = YES
    MERGED -> AttributeCreator_2
    NOT_MERGED -> Logger_2
AttributeCreator_2
    ATTR_LIST = TS_EIB_LEGENDESYMBOL_DE,@Value(REST_IMAGE_URL)
    -> AttributeRemover_4
AttributeRemover_4
    REMOVE_ATTRS = TS_EIB_AUSSAGE_DE,TS_EIB_SORT,GPR_REL_ID,GPR_EBENE,TS_WMS_LAYER,INFO_LAYER,INFO_SYMB_TYP,VALUE,REST_LAYERNAME,REST_LABEL,REST_IMAGE_URL
    -> AttributeRenamer_2
AttributeRenamer_2
    ATTR_LIST = TS_EIB_OID,EIB_OID,"",TS_EIB_LEGENDESYMBOL_DE,EIB_LEGENDESYMBOL_DE,""
    -> PythonCaller_5
PythonCaller_5
    PYTHONSYMBOL = processFeature
    PYTHONSOURCE:
      import fmeobjects
      import os

      def processFeature(feature):
          token = FME_MacroValues['TOKEN']
          symbol_url = feature.getAttribute("EIB_LEGENDESYMBOL_DE")
          unc_base = FME_MacroValues['LEGEND_BASEDIR']
          url_base = FME_MacroValues['LEGEND_BASEURL']

          imagename = symbol_url.split("/images/")[1] + ".png"
          imagename_prefix = symbol_url.split("/images/")[0].split("/MapServer/")[1] + "_"
          filename = imagename_prefix + imagename

          url_file = url_base + filename
          unc_file = os.path.join(unc_base, filename)

          feature.setAttribute("EIB_LEGENDESYMBOL_DE", url_file)
          feature.setAttribute("FILENAME", unc_file)

          if token != '0':
              symbol_url = symbol_url + "?token=" + token
          feature.setAttribute("URL_ORI", symbol_url)
    NEW_ATTRIBUTES = EIB_LEGENDESYMBOL_DE FILENAME URL_ORI
    -> StringConcatenator_2
    -> AttributeRemover_7
AttributeRemover_7
    REMOVE_ATTRS = EIB_OID,EIB_LEGENDESYMBOL_DE
    -> Aggregator
Aggregator
    GROUP_BY = FILENAME URL_ORI
    MODE = Attributes Only
    SEP = ,
    ORDERED = No
    ACCUM_ATTRS_NAME = Yes
    AGGREGATE -> HTTPFetcher_2
HTTPFetcher_2
    SAVE_FILE = Yes
    RESPONSE_HEADER_LIST_ATTR = _headers
    USE_COOKIES = No
    OUTPUT_FILENAME = @Value(FILENAME)
    TARGET_URL = @Value(URL_ORI)
    FOLLOW_REDIRECTS = Yes
    STATUS_CODE_ATTR = _http_status_code
    TARGET_ATTR = _url_contents
    AUTH_METHOD = Basic
    PROXY_AUTH_METHOD = Basic
    VERIFY_SSL_CERTIFICATES = Yes
    ERROR_ATTR = _error
    <REJECTED> -> Terminator_2
Terminator_2
    MESSAGE = Beim Runterladen der Legendenbildli ist etwas schiefgegangen!!!
StringConcatenator_2
    PARM_LINE = EIB_OID='@Value(EIB_OID)'
    VAL_ATTR = fme_where
    -> OEREB2.EIGENTUMSBESCHRAENKUNG (writer ORACLE8I_DB_3)
OEREB2.EIGENTUMSBESCHRAENKUNG (writer ORACLE8I_DB_3)
    attributes: EIB_OID nvarchar(128), EIB_LEGENDESYMBOL_DE nvarchar(1023), EIB_LEGENDESYMBOL_FR nvarchar(1023)
Logger_2
    MAXFEATS = 200
    MESSAGE = Nicht im REST-Dienst gefundene Objekte:
    MAXCOORDS = 20
Logger
    MAXFEATS = 200
    MESSAGE = Nicht in den INFO-Tabellen gefundene Objekte:
    MAXCOORDS = 20

Bookmark: Geoprodukte abfragen
GEODB.NPL_GEFF (reader ORACLE8I_DB_2)
    attributes: OBJECTID number(38,0), BFSNR number(5,0), NAME nvarchar(31), REL_ID nvarchar(100), VERBINDLKT nvarchar(100), ART nvarchar(100), STUFE nvarchar(100), BESCHRIEB nvarchar(80)
    -> AttributeKeeper
GEODB.NPL_GNBAUW (reader ORACLE8I_DB_2)
    attributes: OBJECTID number(38,0), BFSNR number(5,0), NAME nvarchar(31), REL_ID nvarchar(100), GEBLAENGE number(5,0), GEBLANGUNB nvarchar(20), GEBLANGSYM nvarchar(2), GEBTIEFE number(5,0), GEBTIEFUNB nvarchar(20), GEBTIEFSYM nvarchar(2), BAUWEISTYP nvarchar(100)
    -> AttributeKeeper
GEODB.NPL_UEUL (reader ORACLE8I_DB_2)
    attributes: OBJECTID number(38,0), BFSNR number(5,0), NAME nvarchar(31), REL_ID nvarchar(100), VERBINDLKT nvarchar(100), KANTART nvarchar(100), LINIENABK nvarchar(12), LINIENCODE nvarchar(12), BESCHRIEB nvarchar(80), GENEHMDAT date, PLANBESCHR nvarchar(30)
    -> AttributeKeeper
GEODB.NPL_WAABPER (reader ORACLE8I_DB_2)
    attributes: OBJECTID number(38,0), BFSNR number(5,0), NAME nvarchar(31), REL_ID nvarchar(100)
    -> AttributeKeeper
GEODB.NPL_GEGEWF (reader ORACLE8I_DB_2)
    attributes: OBJECTID number(38,0), BFSNR number(5,0), NAME nvarchar(31), REL_ID nvarchar(100), VERBINDLKT nvarchar(100), ART nvarchar(100), BESCHRIEB nvarchar(80)
    -> AttributeKeeper
GEODB.NPL_WEWRF (reader ORACLE8I_DB_2)
    attributes: OBJECTID number(38,0), BFSNR number(5,0), NAME nvarchar(31), REL_ID nvarchar(100), VERBINDLKT nvarchar(100), NAMEWEG nvarchar(80), ART nvarchar(100), BESCHRIEB nvarchar(80)
    -> AttributeKeeper
GEODB.NPL_NHSF (reader ORACLE8I_DB_2)
    attributes: OBJECTID number(38,0), BFSNR number(5,0), NAME nvarchar(31), REL_ID nvarchar(100), VERBINDLKT nvarchar(100), KANTART nvarchar(100), SCHUTZGRAD nvarchar(100), BESCHRIEB nvarchar(80)
    -> AttributeKeeper
GEODB.NPL_WEWRL (reader ORACLE8I_DB_2)
    attributes: OBJECTID number(38,0), BFSNR number(5,0), NAME nvarchar(31), REL_ID nvarchar(100), VERBINDLKT nvarchar(100), NAMEWEG nvarchar(80), ART nvarchar(100), BESCHRIEB nvarchar(80)
    -> AttributeKeeper
GEODB.NPL_GEGEWL (reader ORACLE8I_DB_2)
    attributes: OBJECTID number(38,0), BFSNR number(5,0), NAME nvarchar(31), REL_ID nvarchar(100), VERBINDLKT nvarchar(100), ART nvarchar(100), BESCHRIEB nvarchar(80)
    -> AttributeKeeper
GEODB.NPL_GNGZ (reader ORACLE8I_DB_2)
    attributes: OBJECTID number(38,0), BFSNR number(5,0), NAME nvarchar(31), REL_ID nvarchar(100), VERBINDLKT nvarchar(100), ZONENABK nvarchar(12), ZONENCODE nvarchar(12), ZONENNAME nvarchar(60), KANTZONE nvarchar(100), AZ number(4,2), AZART nvarchar(40)
    -> AttributeKeeper
GEODB.NPL_NHSL (reader ORACLE8I_DB_2)
    attributes: OBJECTID number(38,0), BFSNR number(5,0), NAME nvarchar(31), REL_ID nvarchar(100), VERBINDLKT nvarchar(100), KANTART nvarchar(100), SCHUTZGRAD nvarchar(100), BESCHRIEB nvarchar(80)
    -> AttributeKeeper
GEODB.NPL_UEUZ (reader ORACLE8I_DB_2)
    attributes: OBJECTID number(38,0), BFSNR number(5,0), NAME nvarchar(31), REL_ID nvarchar(100), VERBINDLKT nvarchar(100), KANTART nvarchar(100), ZONENABK nvarchar(12), ZONENCODE nvarchar(12), BESCHRIEB nvarchar(80)
    -> AttributeKeeper
GEODB.NPL_GNNUTZZO (reader ORACLE8I_DB_2)
    attributes: OBJECTID number(38,0), BFSNR number(5,0), NAME nvarchar(31), REL_ID nvarchar(100), VERBINDLKT nvarchar(100), ZONENABK nvarchar(12), ZONENCODE nvarchar(12), ZONENNAME nvarchar(60), KANTZONE nvarchar(100), AZ number(4,2), AZART nvarchar(40), NZTYP nvarchar(100), BKTYP nvarchar(100)
    -> AttributeKeeper
GEODB.NPL_UEPROJ (reader ORACLE8I_DB_2)
    attributes: OBJECTID number(38,0), BFSNR number(5,0), NAME nvarchar(31), REL_ID nvarchar(100), VERBINDLKT nvarchar(100), KANTART nvarchar(100), LINIENABK nvarchar(12), LINIENCODE nvarchar(12), BESCHRIEB nvarchar(80), GENEHMDAT date, PLANBESCHR nvarchar(30)
    -> AttributeKeeper
GEODB.NPL_NHSP (reader ORACLE8I_DB_2)
    attributes: OBJECTID number(38,0), BFSNR number(5,0), NAME nvarchar(31), REL_ID nvarchar(100), VERBINDLKT nvarchar(100), KANTART nvarchar(100), SCHUTZGRAD nvarchar(100), BESCHRIEB nvarchar(80)
    -> AttributeKeeper
GEODB.NPL_VEFE (reader ORACLE8I_DB_2)
    attributes: OBJECTID number(38,0), BFSNR number(5,0), NAME nvarchar(31), REL_ID nvarchar(100), VERBINDLKT nvarchar(100), KANTART nvarchar(100), GUELTIGBIS date, BESCHRIEB nvarchar(80)
    -> AttributeKeeper
GEODB.NPL_UELAERM (reader ORACLE8I_DB_2)
    attributes: OBJECTID number(38,0), BFSNR number(5,0), NAME nvarchar(31), REL_ID nvarchar(100), VERBINDLKT nvarchar(100), KANTART nvarchar(100), ZONENABK nvarchar(12), ZONENCODE nvarchar(12)
    -> AttributeKeeper
GEODB.NPL_UEWAAB (reader ORACLE8I_DB_2)
    attributes: OBJECTID number(38,0), BFSNR number(5,0), NAME nvarchar(31), REL_ID nvarchar(100), VERBINDLKT nvarchar(100), KANTART nvarchar(100), LINIENABK nvarchar(12), LINIENCODE nvarchar(12)
    -> AttributeKeeper
AttributeKeeper
    KEEP_ATTRS = REL_ID,fme_feature_type
    -> AttributeRenamer
AttributeRenamer
    ATTR_LIST = fme_feature_type,EBENE,""
    -> BulkAttributeRenamer_4
BulkAttributeRenamer_4
    ATTRCHOICE = All Attributes
    PATTERN_ACTION_DISP = Add String Prefix
    REPLACE_STR = GPR_
    -> FeatureMerger [SUPPLIER]

FME custom transformer TextBoxAdder

Parameters:
- MINXVALATTR =   # Min X Value
- MINYVALATTR =   # Min Y Value
- MAXXVALATTR =   # Max X Value
- MAXYVALATTR =   # Max Y Value
- HEIGHT = 18   # Label Height
- LabelText =   # Label Text

INPUT (input)
    -> 2DBoxReplacer
Box (output)
Text (output)

Bookmark: Create Box
2DBoxReplacer
    MINYVALATTR = $(MINYVALATTR)
    MINXVALATTR = $(MINXVALATTR)
    MAXYVALATTR = $(MAXYVALATTR)
    MAXXVALATTR = $(MAXXVALATTR)
    BOX -> CenterPointReplacer_2
    BOX -> Box (output)

Bookmark: Add Label
CenterPointReplacer_2
    CENTERPOINT -> CoordinateExtractor_2
CoordinateExtractor_2
    Y_ATTR = _y
    X_ATTR = _x
    IND = 0
    Z_DEFAULT = -9999
    Z_ATTR = _z
    -> AttributeCreator
AttributeCreator
    ATTR_LIST = Font,Arial,$(HEIGHT),Label,$(LabelText)
    -> LabelPointReplacer_2
LabelPointReplacer_2
    HEIGHT = $(HEIGHT)
    ALWAYSROTATE = no
    LABATTR = Label
    LABELPOINT -> BoundingBoxReplacer

Bookmark: Center Justify Label
BoundingBoxReplacer
    BOXTYPE = Bounding Box
    BOX -> CenterPointReplacer
CenterPointReplacer
    CENTERPOINT -> CoordinateExtractor
CoordinateExtractor
    Y_ATTR = _yt
    X_ATTR = _xt
    IND = 0
    Z_DEFAULT = -9999
    Z_ATTR = _zt
    -> 2DPointReplacer
2DPointReplacer
    XVALATTR = @Value(_x)-(@Value(_xt)-@Value(_x))
    YVALATTR = @Value(_y)-(@Value(_yt)-@Value(_y))
    POINT -> LabelPointReplacer
LabelPointReplacer
    HEIGHT = $(HEIGHT)
    ALWAYSROTATE = yes
    LABATTR = Label
    LABELPOINT -> Text (output)

FME custom transformer TableAdder
Generates a vector-based table of attribute data for writing to pdf or other vector formats
Users specify the minimum and maximum coordinates of the table as well as the maximum y coordinate. Attributes to be summarized are selected. A table name can also be given. The length of the table will depend on the number of attributes and the font size specified. Table text and boundaries can be later styled with other styler transformers such as the PDF Styler.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- ChartTitle = Title   # Chart Title
- MINXVALATTR =   # Min X Value
- MAXXVALATTR =   # Max X Value
- MAXYVALATTR =   # Max Y Value
- HEIGHT = 18   # Title Height
- HEIGHT_2 = 12   # Row Text Height
- ATTRLIST =   # Selected Attributes

INPUT (input)
    -> TextBoxAdder_2
    -> ParameterFetcher
Outline (output)
Text (output)

Bookmark: Add Title
TextBoxAdder_2
    MINYVALATTR = $(MAXYVALATTR)-$(HEIGHT)*2
    MINXVALATTR = $(MINXVALATTR)
    LabelText = $(ChartTitle)
    HEIGHT = $(HEIGHT)
    MAXYVALATTR = $(MAXYVALATTR)
    MAXXVALATTR = $(MAXXVALATTR)
    Box -> AttributeRemover_2
    Text -> AttributeRemover

Bookmark: Calculate Number of Columns
ParameterFetcher
    ATTR_LIST = _ATTRLIST {$(ATTRLIST)}
    -> AttributeSplitter
AttributeSplitter
    ATTR_NAME = _ATTRLIST
    LIST_NAME = _list
    DELIMITER = " "
    TRIM_OPTION = Both
    DROP_EMPTY_PARTS = No
    -> ListElementCounter
ListElementCounter
    LIST_NAME = _list{}
    CNT_ATTR = AttributeCount
    -> Counter_5

Bookmark: Explode Cells
Counter_5
    SCOPE = Local
    DOMAIN = counter
    CNT_ATTR = _count
    START = 0
    -> AttributeExploder_2
AttributeExploder_2
    EXPLODING_TYPE = Features
    ATTR_VALUE_LABEL = _attr_value
    ATTR_NAME_LABEL = _attr_name
    KEEP_ATTRIBUTES = Yes
    KEEP_GEOMETRY = No
    -> ListSearcher_2

Bookmark: Add Rows
ListSearcher_2
    ATTR_VALUE = @Value(_attr_name)
    LIST_ATTR = _list{}
    SEARCH_TYPE = First exact match
    INDEX_ATTR = _list_index
    FOUND -> Sorter_2
Sorter_2
    SORT_PARM = _count NUMERIC ASCENDING _list_index NUMERIC ASCENDING
    SORTED -> Counter_3
Counter_3
    SCOPE = Local
    DOMAIN = counter
    CNT_ATTR = _count
    START = 0
    -> TextBoxAdder_3
    -> Tester
TextBoxAdder_3
    MINYVALATTR = $(MAXYVALATTR)-$(HEIGHT)*2-2*$(HEIGHT_2)*(@Value(_count)/(@Value(AttributeCount))+2)
    MINXVALATTR = $(MINXVALATTR)+@double(@Value(_count)%@Value(AttributeCount))*($(MAXXVALATTR)-$(MINXVALATTR))/@Value(AttributeCount)
    LabelText = @Value(_attr_value)
    HEIGHT = $(HEIGHT_2)
    MAXYVALATTR = $(MAXYVALATTR)-$(HEIGHT)*2-2*$(HEIGHT_2)*(@Value(_count)/@Value(AttributeCount)+1)
    MAXXVALATTR = $(MINXVALATTR)+@double(@Value(_count)%@Value(AttributeCount)+1)*($(MAXXVALATTR)-$(MINXVALATTR))/(@Value(AttributeCount))
    Box -> AttributeRemover_2
    Text -> AttributeRemover

Bookmark: Add Header
Tester
    TEST_DESCRIPTION = ""
    TEST_CLAUSE = TEST @Value(_count) < @Value(AttributeCount)
    BOOL_OP = OR
    TEST_MODE = Automatic
    PASSED -> TextBoxAdder
TextBoxAdder
    MINYVALATTR = $(MAXYVALATTR)-$(HEIGHT)*2-2*$(HEIGHT_2)
    MINXVALATTR = $(MINXVALATTR)+@double(@Value(_count))*($(MAXXVALATTR)-$(MINXVALATTR))/@Value(AttributeCount)
    LabelText = @Value(_attr_name)
    HEIGHT = $(HEIGHT_2)
    MAXYVALATTR = $(MAXYVALATTR)-$(HEIGHT)*2
    MAXXVALATTR = $(MINXVALATTR)+@double(@Value(_count)+1)*($(MAXXVALATTR)-$(MINXVALATTR))/@Value(AttributeCount)
    Box -> AttributeRemover_2
    Text -> AttributeRemover

Bookmark: Remove Attributes
AttributeRemover_2
    LIST_ATTRS = _list{}
    REMOVE_ATTRS = _ATTRLIST,AttributeCount,_count,_attr_name,_attr_value,_list_index
    -> Outline (output)
AttributeRemover
    LIST_ATTRS = _list{}
    REMOVE_ATTRS = _ATTRLIST,AttributeCount,_count,_attr_name,_attr_value,_list_index
    -> Text (output)
