FME workspace release_geodb.fmw

Parameters:
- TEAM_DB =   # Team-DB
- WORK_DB =   # Work-Database
- WORK_USERNAME =   # Work-Username
- WORK_PASSWORD =   # Work-Password
- TEAM_USERNAME =   # Team-Username
- TEAM_PASSWORD =   # Team-Password
- ART_CLAUSE =   # Where-Clause TICKETART
- LOGFILE =   # Logfile

Writers:
- ORACLE8I_DB_1: ORACLE8I_DB to $(TEAM_DB)
- ORACLE8I_DB_2: ORACLE8I_DB to $(TEAM_DB)
- ORACLE8I_DB_3: ORACLE8I_DB to $(WORK_DB)

Note: Alle Tickets mit Status=3 und / mit GPRCODE
SQLCreator
    DATASET = $(WORK_DB)
    EXPOSED_ATTRIBUTE_LIST = ART,GEODB_USECASE,ID,NACHFUEHRUNG,GPRCODE
    FORMAT = ORACLE8I_DB
    ORACLE8I_DB_PASSWORD = $(WORK_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(WORK_USERNAME)
    ORACLE8I_DB_USE_UNIFIED_DATE_ATTRS = YES
    SQL_STATEMENT = select t.id, t.NACHFUEHRUNG, t.ART, ta.GEODB_USECASE, wg.gprcode from ticket t left join ticketart ta on t.art=ta.art_id left join liefereinheit le on t.liefereinheit=le.id left join WORKFLOW_GPR wg on le.WORKFLOW=wg.WORKFLOW  where t.STATUS=3 and t.ART$(ART_CLAUSE)
    RESULT -> TestFilter
Note: NPL-Geoprodukte rausfiltern. / Sie werden deaktiviert. / Für sie muss kein iLader-Task / erstellt werden.
TestFilter
    DEFAULT_VALUE = UEBRIGE
    TEST_LIST = BOOL_OP,OR,COMPOSITE_TEST,<Unused>,TEST_CLAUSE,"TEST @Value(GPRCODE) CONTAINS NPL",NPL
    NPL -> TestFilter_NPL
    UEBRIGE -> AttributeFilter
Note: Für TICKETART=4 werden keine Einträge in den / iLader-Tabellen geschrieben. / Es handelt sich um Aktualisierungen mit Zeitstand. / Hierbei werden die Einträge in TB_TASK und TB_FLAG_AGI / nicht vom oerebLader gemacht, sondern von der iLader- / Triggerfunktion. / Stattdessen wird die TASK_OBJECTID ermittelt und in / die TICKET-Tabelle zurückgeschrieben.
AttributeFilter
    ATTR_NAME = ART
    ATTR_VALUES = <EMPTY>,<MISSING>,<NULL>,<UNFILTERED>,1,4
    <UNFILTERED> -> AttributeRemover_2
    1 -> AttributeRemover_2
    1 -> AttributeCreator
    4 -> SQLExecutor_3 [INITIATOR]
Note: OEREBSTA reinschmuggeln!
AttributeCreator
    ATTR_TABLE = SET_TO GPRCODE = OEREBSTA
    -> AttributeRemover_2
Note: GEODB_DD.TB_TASK
TB_TASK (writer ORACLE8I_DB_1)
    attributes: TASK_OBJECTID number(38,0), GZS_OBJECTID number(38,0), UC_OBJECTID number(38,0), TASK_SERVER varchar2(100), TASK_STATUS number(38,0), TASK_START date, TASK_ENDE date, FLAG_OBJECTID number(38,0)
Note: GEODB_DD.TB_FLAG_AGI
TB_FLAG_AGI (writer ORACLE8I_DB_2)
    attributes: FLAG_OBJECTID number(38,0), GPR_BEZEICHNUNG varchar2(100), FLAG_DATUM date, TASK_OBJECTID number(38,0)
TICKET (writer ORACLE8I_DB_3)
    attributes: TASK_ID_GEODB number(38,0)
TestFilter_NPL: Logger
    MAXCOORDS = 20
    MAXFEATS = 20
    MESSAGE = Z.Z. nicht importierte Geoprodukte:

Bookmark: Nachführungsdatum (= Release-Datum)
AttributeRemover_2
    REMOVE_ATTRS = ART,NACHFUEHRUNG
    -> TimeStamper
TimeStamper
    FMT = FME Date (^Y^m^d)
    TIME_ATTR = NACHFUEHRUNG
    -> Aggregator

Bookmark: GeoDB-DD-Informationen holen
Note: Gruppieren nach GPR. Es wird nicht / mehr nach ART gruppiert.
Aggregator
    ACCUM_ATTRS_NAME = Merge Incoming Attributes
    CONCAT_ATTRS = ID
    GROUP_BY = GPRCODE NACHFUEHRUNG GEODB_USECASE
    MODE = Attributes Only
    ORDERED = No
    SEP = ,
    AGGREGATE -> SQLExecutor [INITIATOR]
Note: TASK_OBJECTID holen
SQLExecutor
    COMBINE_ATTRS = Keep Initiator Attributes if Conflict
    COMBINE_GEOM = Initiator Geometry Only
    DATASET = $(TEAM_DB)
    EXPOSED_ATTRIBUTE_LIST = TASK_OBJECTID
    FORMAT = ORACLE8I_DB
    ORACLE8I_DB_PASSWORD = $(TEAM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(TEAM_USERNAME)
    ORACLE8I_DB_USE_UNIFIED_DATE_ATTRS = YES
    SQL_STATEMENT = select GDBBE_SEQ.NEXTVAL as TASK_OBJECTID FROM dual
    RESULT -> SQLExecutor_2 [INITIATOR]
Note: FLAG_OBJECTID holen
SQLExecutor_2
    COMBINE_ATTRS = Keep Initiator Attributes if Conflict
    COMBINE_GEOM = Initiator Geometry Only
    DATASET = $(TEAM_DB)
    EXPOSED_ATTRIBUTE_LIST = FLAG_OBJECTID
    FORMAT = ORACLE8I_DB
    ORACLE8I_DB_PASSWORD = $(TEAM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(TEAM_USERNAME)
    ORACLE8I_DB_USE_UNIFIED_DATE_ATTRS = YES
    SQL_STATEMENT = select GDBBE_SEQ.NEXTVAL as FLAG_OBJECTID FROM dual
    RESULT -> Joiner
Note: GZS_OBJECTID holen
Joiner
    ADDED_FIELDS = GZS_OBJECTID
    ATTR_ACCUM_MODE = Merge Joined
    ATTR_CONFLICT_RES = Use Original
    CACHE_SIZE = 5000
    DATASET = $(TEAM_DB)
    FORMAT = ORACLE8I_DB
    JOIN_KEYS = GPRCODE GPR_BEZEICHNUNG
    MATCH_RULE_DISPLAY = Must Match Exactly One (1:1)
    ORACLE8I_DB_PASSWORD = $(TEAM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(TEAM_USERNAME)
    ORACLE8I_DB_USE_UNIFIED_DATE_ATTRS = YES
    PREFETCH_EXHAUSTIVE = Yes
    TABLE = GEODB_DD.TB_GEOPRODUKT
    JOINED -> Joiner_2
Note: UC_STARTSTATUS holen
Joiner_2
    ADDED_FIELDS = UC_STARTSTATUS
    ATTR_ACCUM_MODE = Merge Joined
    ATTR_CONFLICT_RES = Use Original
    CACHE_SIZE = 5000
    DATASET = $(TEAM_DB)
    FORMAT = ORACLE8I_DB
    JOIN_KEYS = GEODB_USECASE UC_OBJECTID
    MATCH_RULE_DISPLAY = Must Match Exactly One (1:1)
    ORACLE8I_DB_PASSWORD = $(TEAM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(TEAM_USERNAME)
    ORACLE8I_DB_USE_UNIFIED_DATE_ATTRS = YES
    PREFETCH_EXHAUSTIVE = Yes
    TABLE = GEODB_DD.TB_USECASE
    JOINED -> AttributeRenamer
AttributeRenamer
    ATTR_TABLE:
      RENAME_SET_DEFAULT GEODB_USECASE > UC_OBJECTID
      RENAME_SET_DEFAULT NACHFUEHRUNG > FLAG_DATUM
      RENAME_SET_DEFAULT GPRCODE > GPR_BEZEICHNUNG
      RENAME_SET_DEFAULT UC_STARTSTATUS > TASK_STATUS
    -> TB_FLAG_AGI (writer ORACLE8I_DB_2)
    -> AttributeFilter_2
    -> TB_TASK (writer ORACLE8I_DB_1)

Bookmark: GeoDB-Taskid zurückschreiben
Note: OEREBSTA rausfiltern. / Es wird nicht zurückgeschrieben.
AttributeFilter_2
    ATTR_NAME = GPR_BEZEICHNUNG
    ATTR_VALUES = <EMPTY>,<MISSING>,<NULL>,<UNFILTERED>,OEREBSTA
    <UNFILTERED> -> AttributeRemover_3
AttributeRemover_3
    REMOVE_ATTRS = ART,UC_OBJECTID,GPR_BEZEICHNUNG,FLAG_DATUM,FLAG_OBJECTID,GZS_OBJECTID,_matched_records,TASK_STATUS
    -> AttributeSplitter
AttributeSplitter
    ATTR_NAME = ID
    DELIMITER = ,
    DROP_EMPTY_PARTS = No
    LIST_NAME = _tickets
    TRIM_OPTION = Both
    -> ListExploder
ListExploder
    ATTR_ACCUM_MODE = Merge Incoming List
    ATTR_CONFLICT_RES = Use Incoming List
    INDEX_ATTR = _element_index
    LIST_ATTR = _tickets{}
    ELEMENTS -> StringConcatenator
StringConcatenator
    ACTION = Create New Attribute
    PARM_LINE = ID=@Value(_tickets)
    VAL_ATTR = fme_where
    -> AttributeRemover_4
AttributeRemover_4
    REMOVE_ATTRS = ID,_tickets,_element_index
    -> AttributeRenamer_2
AttributeRenamer_2
    ATTR_TABLE = RENAME_SET_DEFAULT TASK_OBJECTID > TASK_ID_GEODB
    -> TICKET (writer ORACLE8I_DB_3)

Bookmark: GeoDB-Taskid ermitteln und zurückschreiben
SQLExecutor_3
    COMBINE_ATTRS = Keep Initiator Attributes if Conflict
    COMBINE_GEOM = Initiator Geometry Only
    DATASET = $(TEAM_DB)
    EXPOSED_ATTRIBUTE_LIST = TASK_OBJECTID
    FORMAT = ORACLE8I_DB
    ORACLE8I_DB_PASSWORD = $(TEAM_PASSWORD)
    ORACLE8I_DB_PERSISTENT_CONNECTION = YES
    ORACLE8I_DB_QUERY_FEATURE_TYPES_FOR_MERGE_FILTERS = Yes
    ORACLE8I_DB_REMOVE_SCHEMA_QUALIFIER = NO
    ORACLE8I_DB_SERVER_TYPE = ORACLE8i
    ORACLE8I_DB_SHOW_SYSTEM_TABLES = NO
    ORACLE8I_DB_USER_NAME = $(TEAM_USERNAME)
    ORACLE8I_DB_USE_UNIFIED_DATE_ATTRS = YES
    SQL_STATEMENT = select tsk.TASK_OBJECTID from tb_task tsk join vw_geoprodukt_zeitstand gzs on tsk.GZS_OBJECTID=gzs.GZS_OBJECTID where tsk.TASK_STATUS=1 and tsk.UC_OBJECTID in (1,2,3,4) and gzs.gpr_bezeichnung='@Value(GPRCODE)'
    RESULT -> AttributeRenamer_3
AttributeRenamer_3
    ATTR_TABLE = RENAME_SET_DEFAULT TASK_OBJECTID > TASK_ID_GEODB
    -> StringConcatenator_2
StringConcatenator_2
    ACTION = Create New Attribute
    PARM_LINE = ID=@Value(ID)
    VAL_ATTR = fme_where
    -> AttributeRemover_5
AttributeRemover_5
    REMOVE_ATTRS = ART,GEODB_USECASE,GPRCODE,ID,NACHFUEHRUNG
    -> TICKET (writer ORACLE8I_DB_3)
